-- $Id: X2AP-Constants.asn 23886 2007-12-16 14:26:18Z etxrab $
-- 3GPP TS 36.423 V8.0.0 (2007-12)
-- 9.3.7	Constant Definitions
-- **************************************************************
--
-- Constant definitions
--
-- **************************************************************

X2AP-Constants {
itu-t (0) identified-organization (4) etsi (0) mobileDomain (0) 
eps-Access (21) modules (3) x2ap (2) version1 (1) x2ap-Constants (4) }

DEFINITIONS AUTOMATIC TAGS ::= 

BEGIN

IMPORTS
	ProcedureCode,
	ProtocolIE-ID
FROM X2AP-CommonDataTypes;

-- **************************************************************
--
-- Elementary Procedures
--
-- **************************************************************

id-handoverPreparation											ProcedureCode ::= 0
id-handoverCancel												ProcedureCode ::= 1
id-loadIndication												ProcedureCode ::= 2
id-errorIndication												ProcedureCode ::= 3
id-snStatusTransfer												ProcedureCode ::= 4
id-releaseResource												ProcedureCode ::= 5
id-x2Setup														ProcedureCode ::= 6
id-reset														ProcedureCode ::= 7



-- **************************************************************
--
-- Lists
--
-- **************************************************************

maxInterfaces								INTEGER ::= 16		-- FFS Value to be checked
maxCellineNB								INTEGER ::= 256		-- FFS Value to be checked
maxnoofCells								INTEGER ::= 16		-- FFS Value to be checked
maxnoofBearers								INTEGER ::= 16		-- FFS Value to be checked
maxNrOfErrors								INTEGER ::= 256		-- FFS Value to be checked
maxnoofPDCP-SN								INTEGER ::= 16		-- FFS Value to be checked
maxnoofEPLMNs								INTEGER ::= 15		
maxnoofEPLMNsPlusOne						INTEGER ::= 16		
maxnoofForbLACs								INTEGER ::= 256		-- FFS Value to be checked
maxnoofForbTAIs								INTEGER ::= 256		-- FFS Value to be checked
maxnoofBPLMNs								INTEGER ::= 6




-- **************************************************************
--
-- IEs
--
-- **************************************************************

id-Bearers-Admitted-Item													ProtocolIE-ID ::= 0
id-Bearers-Admitted-List													ProtocolIE-ID ::= 1
id-Bearers-NotAdmitted-Item													ProtocolIE-ID ::= 2
id-Bearers-NotAdmitted-List													ProtocolIE-ID ::= 3
id-Bearers-ToBeSetup-Item													ProtocolIE-ID ::= 4
id-Cause																	ProtocolIE-ID ::= 5
id-CellInformation															ProtocolIE-ID ::= 6
id-CellInformation-Item														ProtocolIE-ID ::= 7
id-InterfacesToTrace-Item													ProtocolIE-ID ::= 8
id-New-eNB-UE-X2AP-ID														ProtocolIE-ID ::= 9
id-Old-eNB-UE-X2AP-ID														ProtocolIE-ID ::= 10
id-TargetCell-ID															ProtocolIE-ID ::= 11
id-TargeteNBtoSource-eNBTransparentContainer								ProtocolIE-ID ::= 12
id-TraceActivation															ProtocolIE-ID ::= 13
id-UE-ContextInformation													ProtocolIE-ID ::= 14
id-UE-HistoryInformation													ProtocolIE-ID ::= 15
id-UE-X2AP-ID																ProtocolIE-ID ::= 16
id-CriticalityDiagnostics													ProtocolIE-ID ::= 17
id-Bearers-SubjectToStatusTransfer-List										ProtocolIE-ID ::= 18
id-Bearers-SubjectToStatusTransfer-Item										ProtocolIE-ID ::= 19
id-ServedCells																ProtocolIE-ID ::= 20
id-ENB-ID																	ProtocolIE-ID ::= 21
id-TimeToWait																ProtocolIE-ID ::= 22


END
