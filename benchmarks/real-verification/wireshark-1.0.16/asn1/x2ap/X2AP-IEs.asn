-- $Id: X2AP-IEs.asn 24097 2008-01-15 17:59:43Z etxrab $
-- 3GPP TS 36.423 V8.0.0 (2007-12)
-- 9.3.5	Information Element Definitions
-- **************************************************************
--
-- Information Element Definitions
--
-- **************************************************************

X2AP-IEs {
itu-t (0) identified-organization (4) etsi (0) mobileDomain (0) 
eps-Access (21) modules (3) x2ap (2) version1 (1) x2ap-IEs (2) }

DEFINITIONS AUTOMATIC TAGS ::= 

BEGIN

IMPORTS
	id-InterfacesToTrace-Item,
	maxInterfaces,
	maxNrOfErrors,
	maxnoofCells,
	maxnoofEPLMNs,
	maxnoofEPLMNsPlusOne,
	maxnoofForbLACs,
	maxnoofForbTAIs,
	maxCellineNB,
	maxnoofBPLMNs

FROM X2AP-Constants

	Criticality,
	ProcedureCode,
	ProtocolIE-ID,
	TriggeringMessage
FROM X2AP-CommonDataTypes

	ProtocolIE-Single-Container{},
	ProtocolExtensionContainer{},
	X2AP-PROTOCOL-IES,
	X2AP-PROTOCOL-EXTENSION
FROM X2AP-Containers;

-- A

AggregateMaximumBitRate ::= SEQUENCE {
	aggregateMaximumBitRateDownlink		SAE-Bearer-BitRate,
	aggregateMaximumBitRateUplink		SAE-Bearer-BitRate,
	...
}

-- B

Bearer-ID ::= BIT STRING (SIZE (8))  -- To be checked, FFS

BroadcastPLMNs-Item ::= SEQUENCE (SIZE(1..maxnoofBPLMNs)) OF PLMN-Identity


-- C

Cause ::= CHOICE {
	radioNetwork		CauseRadioNetwork,
	transport			CauseTransport,
	protocol			CauseProtocol,
	misc				CauseMisc,
	...
}

CauseMisc ::= ENUMERATED {
	control-processing-overload,
	hardware-failure,
	om-intervention,
	not-enough-user-plane-processing-resources,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unspecified,
	...

}

CauseTransport ::= ENUMERATED {
	transport-resource-unavailable,
	unspecified,
	...
}

CellType ::= ENUMERATED{ 
	macro, 
	micro, 
	pico, 
	femto,
	...
}

CellId ::= OCTET STRING



CGI ::= SEQUENCE {
	pLMN-Identity			PLMN-Identity,
	lAC						LAC,
	cI						CI,
	iE-Extensions			ProtocolExtensionContainer { {CGI-ExtIEs} } OPTIONAL
}

CGI-ExtIEs X2AP-PROTOCOL-EXTENSION ::= {
	...
}

CI					::= OCTET STRING (SIZE (2))

CriticalityDiagnostics ::= SEQUENCE {
	procedureCode					ProcedureCode					OPTIONAL,
	triggeringMessage				TriggeringMessage				OPTIONAL,
	procedureCriticality			Criticality						OPTIONAL,
	iEsCriticalityDiagnostics		CriticalityDiagnostics-IE-List	OPTIONAL,
	iE-Extensions					ProtocolExtensionContainer { {CriticalityDiagnostics-ExtIEs} } OPTIONAL,
	...
}

CriticalityDiagnostics-ExtIEs X2AP-PROTOCOL-EXTENSION ::= {
	...
}

CriticalityDiagnostics-IE-List ::= SEQUENCE (SIZE (1..maxNrOfErrors)) OF
	SEQUENCE {
		iECriticality			Criticality,
		iE-ID					ProtocolIE-ID,
		typeOfError				TypeOfError,
		iE-Extensions			ProtocolExtensionContainer { {CriticalityDiagnostics-IE-List-ExtIEs} } OPTIONAL,
		...
	}

CriticalityDiagnostics-IE-List-ExtIEs X2AP-PROTOCOL-EXTENSION ::= {
	...
}



-- D

DL-data-received ::= INTEGER

DL-Forwarding ::= ENUMERATED {
	dL-forwardingProposed,
	...
}

-- E

ENB-ID							::= INTEGER (0..65535)  -- Value to be checked FFS

EPLMNs ::= SEQUENCE (SIZE(1..maxnoofEPLMNs)) OF PLMN-Identity


-- F

ForbiddenInterRATs ::= ENUMERATED {
	all,
	gsm,
	wcdma,
	...
}

ForbiddenTAs ::= SEQUENCE (SIZE(1.. maxnoofEPLMNsPlusOne)) OF ForbiddenTAs-Item

ForbiddenTAs-Item ::= SEQUENCE {
	pLMN-Identity		PLMN-Identity,
	forbiddenTAIs		ForbiddenTAIs
}

ForbiddenTAIs ::= SEQUENCE (SIZE(1..maxnoofForbTAIs)) OF TAI

ForbiddenLAs ::= SEQUENCE (SIZE(1..maxnoofEPLMNsPlusOne)) OF ForbiddenLAs-Item

ForbiddenLAs-Item ::= SEQUENCE {	
	pLMN-Identity		PLMN-Identity,
	forbiddenLACs		ForbiddenLACs
}

ForbiddenLACs ::= SEQUENCE (SIZE(1..maxnoofForbLACs)) OF LAC

Frequency ::= OCTET STRING


-- G


GTPtunnelEndpoint ::= SEQUENCE {
	transportLayerAddress			TransportLayerAddress,
	gTP-TEID						GTP-TEI,
	iE-Extensions					ProtocolExtensionContainer { {GTPtunnelEndpoint-ExtIEs} } OPTIONAL,
	...
}

GTPtunnelEndpoint-ExtIEs X2AP-PROTOCOL-EXTENSION ::= {
	...
}

GTP-TEI					::= OCTET STRING (SIZE (4))

-- H

HandoverRestrictionList ::= SEQUENCE {
	equivalentPLMNs				EPLMNs					OPTIONAL,
	forbiddenTAs				ForbiddenTAs			OPTIONAL,
	forbiddenLAs				ForbiddenLAs			OPTIONAL,
	forbiddenInterRATs			ForbiddenInterRATs		OPTIONAL, 
	iE-Extensions				ProtocolExtensionContainer { {HandoverRestrictionList-ExtIEs} } OPTIONAL,
	...
}

HandoverRestrictionList-ExtIEs X2AP-PROTOCOL-EXTENSION ::= {
	...
}


-- I


InterfacesToTrace ::= SEQUENCE (SIZE(0..maxInterfaces)) OF ProtocolIE-Single-Container {{InterfacesToTrace-ItemIEs} }

InterfacesToTrace-ItemIEs X2AP-PROTOCOL-IES ::= {
	{ ID id-InterfacesToTrace-Item	CRITICALITY ignore	TYPE InterfacesToTrace-Item 	PRESENCE mandatory	}
}

InterfacesToTrace-Item ::= SEQUENCE {
	traceInterface					TraceInterface,
	traceDepth						TraceDepth,
	iE-Extensions					ProtocolExtensionContainer { {InterfacesToTrace-Item-ExtIEs} } OPTIONAL,
	...
}

InterfacesToTrace-Item-ExtIEs X2AP-PROTOCOL-EXTENSION ::= {
	...
}

InterferenceOverloadIndication ::= OCTET STRING  -- FFS

-- J
-- K
-- L

LAC					::= OCTET STRING (SIZE (2)) --(EXCEPT ('0000'H|'FFFE'H))

LastVisitedCell-Item ::= SEQUENCE {
	global-Cell-ID					CGI,
	cellType						CellType,
	time-UE-StayedInCell			Time-UE-StayedInCell	OPTIONAL,
	iE-Extensions					ProtocolExtensionContainer { {LastVisitedCell-Item-ExtIEs} } OPTIONAL,
	...
}

LastVisitedCell-Item-ExtIEs X2AP-PROTOCOL-EXTENSION ::= {
	...
}


-- M
-- N


-- O
-- P

PDCP-SN ::= INTEGER  -- FFS

PhyCID ::= OCTET STRING


PLMN-Identity ::= OCTET STRING (SIZE(3))

-- Q
-- R

RB-type ::= INTEGER
-- Editors note: FFS To be replaced by other QCI definition, ENUMERATED??

RRC-Context ::= OCTET STRING

-- S

SAE-Bearer-BitRate ::= INTEGER (0..210000000000)

SAE-BearerLevel-QoS-Parameters ::= SEQUENCE {
	label				INTEGER (1..256),
	allocationAndRetentionPriority	OCTET STRING,  --FFS
	sAE-BearerType			SAE-BearerType,
	...
}


SAE-BearerType ::= CHOICE {
	sAE-GBR-bearer		SAE-GBR-Bearer,
	sAE-non-GBR-bearer		SAE-Non-GBR-Bearer,
	...
}

SAE-GBR-Bearer ::= SEQUENCE {
	sAE-Bearer-MaximumBitrateDL			SAE-Bearer-BitRate,
	sAE-Bearer-MaximumBitrateUL			SAE-Bearer-BitRate,
	sAE-Bearer-GuaranteedBitrateDL		SAE-Bearer-BitRate,
	sAE-Bearer-GuaranteedBitrateUL		SAE-Bearer-BitRate,
	iE-Extensions						ProtocolExtensionContainer { {SAE-GBR-Bearer-Parameters-ExtIEs} } OPTIONAL,
	...
}

SAE-GBR-Bearer-Parameters-ExtIEs S1AP-PROTOCOL-EXTENSION ::= {
	...
}


SAE-Non-GBR-Bearer ::= SEQUENCE {
	sAE-non-GBR-Bearer-Type			ENUMERATED {non-GBR-Bearer,...},
	iE-Extensions						ProtocolExtensionContainer { {SAE-non-GBR-Bearer-Parameters-ExtIEs} } OPTIONAL,
	...
}

SAE-non-GBR-Bearer-Parameters-ExtIEs S1AP-PROTOCOL-EXTENSION ::= {
	...
}


ServedCells		::= SEQUENCE (SIZE (1..maxCellineNB)) OF ServedCell-Information


ServedCell-Information ::= SEQUENCE {
	phyCID				PhyCID,
	cellId				CellId,
	tAI					TAI,
	broadcastPLMNs		BroadcastPLMNs-Item,
	frequency			Frequency,
	iE-Extensions		ProtocolExtensionContainer { {ServedCell-Information-ExtIEs} } OPTIONAL,
	...
}

ServedCell-Information-ExtIEs X2AP-PROTOCOL-EXTENSION ::= {
	...
}


-- T

TAI ::= OCTET STRING 	-- FFS

TargeteNBtoSource-eNBTransparentContainer	::= OCTET STRING

Time-UE-StayedInCell ::= INTEGER

TimeToWait ::= OCTET STRING


TraceActivation ::= SEQUENCE {
	traceReference					TraceReference,
	interfacesToTrace				InterfacesToTrace,
	iE-Extensions					ProtocolExtensionContainer { {TraceActivation-ExtIEs} } OPTIONAL,
	...
}

TraceActivation-ExtIEs X2AP-PROTOCOL-EXTENSION ::= {
	...
}



TraceDepth 		::= ENUMERATED { 
	minimum,
	medium,
	maximum,
	...
}

TraceInterface		::= ENUMERATED { 
	s1,
	x2, 
	uu,
	...
}

TraceReference					::= OCTET STRING (SIZE (3))


TransportLayerAddress			::= BIT STRING (SIZE(1..160, ...))

TypeOfError ::= ENUMERATED {
	not-understood,
	missing,
	...
}


-- U

UE-HistoryInformation ::= SEQUENCE (SIZE(1..maxnoofCells)) OF LastVisitedCell-Item


UE-S1AP-ID					::= INTEGER (0..4095) -- Value FFS

UE-X2AP-ID					::= INTEGER (0..4095) -- Value FFS




-- V
-- W
-- X
-- Y
-- Z

END
