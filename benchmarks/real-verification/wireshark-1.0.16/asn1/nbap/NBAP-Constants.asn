-- NBAP-Constants.asn
--
-- Taken from 3GPP TS 25.433 V7.7.0 (2007-12)
-- http://www.3gpp.org/ftp/Specs/archive/25_series/25.433/25433-770.zip/25433-770.DOC
---
-- 9.3.6	Constant Definitions
--
-- $Id: NBAP-Constants.asn 24256 2008-02-03 13:47:50Z etxrab $
--

-- **************************************************************
--
-- Constant definitions
--
-- **************************************************************

NBAP-Constants {
itu-t (0) identified-organization (4) etsi (0) mobileDomain (0) 
umts-Access (20) modules (3) nbap (2) version1 (1) nbap-Constants (4)}

DEFINITIONS AUTOMATIC TAGS ::= 

BEGIN

IMPORTS
	ProcedureCode,
	ProtocolIE-ID
FROM NBAP-CommonDataTypes;

-- **************************************************************
--
-- Elementary Procedures
--
-- **************************************************************

id-audit 												ProcedureCode ::= 0
id-auditRequired 										ProcedureCode ::= 1
id-blockResource 										ProcedureCode ::= 2
id-cellDeletion 										ProcedureCode ::= 3
id-cellReconfiguration 									ProcedureCode ::= 4
id-cellSetup 											ProcedureCode ::= 5
id-cellSynchronisationInitiation						ProcedureCode ::= 45
id-cellSynchronisationReconfiguration					ProcedureCode ::= 46
id-cellSynchronisationReporting							ProcedureCode ::= 47
id-cellSynchronisationTermination						ProcedureCode ::= 48
id-cellSynchronisationFailure							ProcedureCode ::= 49
id-commonMeasurementFailure 							ProcedureCode ::= 6
id-commonMeasurementInitiation 							ProcedureCode ::= 7
id-commonMeasurementReport 								ProcedureCode ::= 8
id-commonMeasurementTermination 						ProcedureCode ::= 9
id-commonTransportChannelDelete 						ProcedureCode ::= 10
id-commonTransportChannelReconfigure 					ProcedureCode ::= 11
id-commonTransportChannelSetup 							ProcedureCode ::= 12
id-compressedModeCommand 								ProcedureCode ::= 14
id-dedicatedMeasurementFailure 							ProcedureCode ::= 16
id-dedicatedMeasurementInitiation 						ProcedureCode ::= 17
id-dedicatedMeasurementReport 							ProcedureCode ::= 18
id-dedicatedMeasurementTermination 						ProcedureCode ::= 19
id-downlinkPowerControl 								ProcedureCode ::= 20
id-downlinkPowerTimeslotControl 						ProcedureCode ::= 38
id-errorIndicationForCommon								ProcedureCode ::= 35
id-errorIndicationForDedicated							ProcedureCode ::= 21
id-informationExchangeFailure							ProcedureCode ::= 40
id-informationExchangeInitiation						ProcedureCode ::= 41
id-informationExchangeTermination						ProcedureCode ::= 42
id-informationReporting									ProcedureCode ::= 43
id-BearerRearrangement									ProcedureCode ::= 50
id-mBMSNotificationUpdate								ProcedureCode ::= 53
id-physicalSharedChannelReconfiguration 				ProcedureCode ::= 37
id-privateMessageForCommon								ProcedureCode ::= 36
id-privateMessageForDedicated							ProcedureCode ::= 22
id-radioLinkAddition 									ProcedureCode ::= 23
id-radioLinkDeletion 									ProcedureCode ::= 24
id-radioLinkFailure 									ProcedureCode ::= 25
id-radioLinkPreemption									ProcedureCode ::= 39
id-radioLinkRestoration 								ProcedureCode ::= 26
id-radioLinkSetup 										ProcedureCode ::= 27
id-reset												ProcedureCode ::= 13
id-resourceStatusIndication 							ProcedureCode ::= 28
id-cellSynchronisationAdjustment						ProcedureCode ::= 44
id-synchronisedRadioLinkReconfigurationCancellation		ProcedureCode ::= 29
id-synchronisedRadioLinkReconfigurationCommit			ProcedureCode ::= 30
id-synchronisedRadioLinkReconfigurationPreparation 		ProcedureCode ::= 31
id-systemInformationUpdate 								ProcedureCode ::= 32
id-unblockResource 										ProcedureCode ::= 33
id-unSynchronisedRadioLinkReconfiguration 				ProcedureCode ::= 34
id-radioLinkActivation									ProcedureCode ::= 51
id-radioLinkParameterUpdate								ProcedureCode ::= 52

-- **************************************************************
--
-- Lists
--
-- **************************************************************

maxNrOfCodes				INTEGER ::= 10
maxNrOfDLTSs				INTEGER ::= 15
maxNrOfDLTSLCRs				INTEGER ::= 6
maxNrOfErrors				INTEGER ::= 256
maxNrOfTFs					INTEGER ::= 32
maxNrOfTFCs					INTEGER ::= 1024
maxNrOfRLs					INTEGER ::= 16
maxNrOfRLs-1				INTEGER ::= 15	-- maxNrOfRLs - 1
maxNrOfRLs-2				INTEGER ::= 14	-- maxNrOfRLs - 2
maxNrOfRLSets				INTEGER ::= maxNrOfRLs
maxNrOfDPCHs				INTEGER ::= 240
maxNrOfDPCHsPerRL-1			INTEGER ::= 239 -- maxNrofCCTrCH*maxNrOfULTSs-1
maxNrOfDPCHLCRs				INTEGER ::= 240
maxNrOfDPCHsLCRPerRL-1		INTEGER ::= 95  -- maxNrofCCTrCH*maxNrOfULTSLCRs-1
maxNrOfDPCHs768				INTEGER ::= 480
maxNrOfDPCHs768PerRL-1		INTEGER ::= 479
maxNrOfSCCPCHs				INTEGER ::= 8
maxNrOfSCCPCHsinExt			INTEGER ::= 232
maxNrOfSCCPCHs768			INTEGER ::= 480
maxNrOfDCHs					INTEGER ::= 128
maxNrOfDSCHs				INTEGER ::= 32
maxNrOfFACHs				INTEGER ::= 8
maxNrOfCCTrCHs				INTEGER ::= 16
maxNrOfPDSCHs				INTEGER ::= 256
maxNrOfHSPDSCHs				INTEGER ::= 16
maxNrOfHSPDSCHs768			INTEGER ::= 32
maxNrOfPUSCHs				INTEGER ::= 256
maxNrOfPUSCHs-1				INTEGER ::= 255
maxNrOfPDSCHSets			INTEGER ::= 256
maxNrOfPRACHLCRs			INTEGER ::= 8
maxNrOfPUSCHSets			INTEGER ::= 256
maxNrOfSCCPCHLCRs			INTEGER ::= 8
maxNrOfSCCPCHsLCRinExt		INTEGER ::= 88
maxNrOfULTSs				INTEGER ::= 15
maxNrOfULTSLCRs				INTEGER ::= 6
maxNrOfUSCHs				INTEGER ::= 32
maxNrOfSlotFormatsPRACH		INTEGER ::= 8
maxCellinNodeB				INTEGER ::= 256
maxCCPinNodeB				INTEGER ::= 256
maxCTFC						INTEGER ::= 16777215
maxLocalCellinNodeB			INTEGER ::= maxCellinNodeB
maxFPACHCell				INTEGER ::= 8
maxRACHCell					INTEGER ::= maxPRACHCell
maxPLCCHCell				INTEGER ::= 16
maxPRACHCell				INTEGER ::= 16
maxSCCPCHCell				INTEGER ::= 32
maxSCCPCHCellinExt			INTEGER ::= 208	-- maxNrOfSCCPCHs + maxNrOfSCCPCHsinExt - maxSCCPCHCell
maxSCCPCHCellinExtLCR		INTEGER ::= 64	-- maxNrOfSCCPCHLCRs + maxNrOfSCCPCHsLCRinExt - maxSCCPCHCell
maxSCCPCHCell768			INTEGER ::= 480
maxSCPICHCell				INTEGER ::= 32
maxTTI-count				INTEGER ::= 4
maxIBSEG					INTEGER ::= 16
maxIB						INTEGER ::= 64
maxFACHCell 				INTEGER ::= 256	-- maxNrOfFACHs * maxSCCPCHCell
maxRateMatching				INTEGER ::= 256
maxHS-PDSCHCodeNrComp-1		INTEGER ::= 15
maxHS-SCCHCodeNrComp-1		INTEGER ::= 127
maxNrOfCellSyncBursts		INTEGER ::= 10
maxNrOfReceptsPerSyncFrame	INTEGER ::= 16
maxNrOfMeasNCell			INTEGER ::= 96
maxNrOfMeasNCell-1			INTEGER ::= 95	-- maxNrOfMeasNCell - 1
maxNrOfSF					INTEGER ::= 8
maxTGPS						INTEGER ::= 6
maxCommunicationContext		INTEGER ::= 1048575
maxNrOfLevels				INTEGER ::= 256
maxNoSat					INTEGER ::= 16
maxNoGPSItems				INTEGER ::= 8
maxNrOfHSSCCHs				INTEGER ::= 32
maxNrOfHSSICHs				INTEGER ::= 4
maxNrOfHSSICHs-1			INTEGER ::= 3
maxNrOfSyncFramesLCR		INTEGER ::= 512
maxNrOfReceptionsperSyncFrameLCR	INTEGER ::=	8
maxNrOfSyncDLCodesLCR		INTEGER ::= 32
maxNrOfHSSCCHCodes				INTEGER ::= 4
maxNrOfMACdFlows				INTEGER ::= 8
maxNrOfMACdFlows-1				INTEGER ::= 7	-- maxNrOfMACdFlows - 1
maxNrOfMACdPDUIndexes			INTEGER ::= 8
maxNrOfMACdPDUIndexes-1			INTEGER ::= 7	-- maxNoOfMACdPDUIndexes - 1
maxNrOfMACdPDUSize				INTEGER ::= 32
maxNrOfNIs						INTEGER ::= 256
maxNrOfPriorityQueues			INTEGER ::= 8
maxNrOfPriorityQueues-1			INTEGER ::= 7	-- maxNoOfPriorityQueues - 1
maxNrOfHARQProcesses			INTEGER ::= 8
maxNrOfContextsOnUeList			INTEGER ::= 16
maxNrOfCellPortionsPerCell		INTEGER ::= 64
maxNrOfCellPortionsPerCell-1	INTEGER ::= 63
maxNrOfPriorityClasses			INTEGER ::= 16
maxNrOfSatAlmanac-maxNoSat		INTEGER ::= 16  -- maxNrofSatAlmanac - maxNoSat
maxNrOfE-AGCHs					INTEGER ::= 32
maxNrOfEDCHMACdFlows			INTEGER ::= 8
maxNrOfEDCHMACdFlows-1			INTEGER ::= 7
maxNrOfE-RGCHs-E-HICHs			INTEGER ::= 32
maxNrOfEDCH-HARQ-PO-QUANTSTEPs	INTEGER ::= 6
maxNrOfEDCHHARQProcesses2msEDCH	INTEGER ::= 8
maxNrOfEDPCCH-PO-QUANTSTEPs		INTEGER ::= 8
maxNrOfBits-MACe-PDU-non-scheduled	INTEGER ::= 19982
maxNrOfRefETFCIs				INTEGER ::= 8
maxNrOfRefETFCI-PO-QUANTSTEPs	INTEGER ::= 29
maxNrofSigSeqRGHI-1				INTEGER ::= 39
maxNoOfLogicalChannels			INTEGER ::= 16 -- only maximum 15 can be used
maxNrOfCombEDPDCH				INTEGER ::= 12
maxE-RUCCHCell					INTEGER ::= 16
maxNrOfEAGCHCodes				INTEGER ::= 4
maxNrOfRefBetas					INTEGER ::= 8
maxNrOfE-PUCHSlots				INTEGER ::= 13
maxNrOfEAGCHs					INTEGER ::= 32
maxNrOfHS-DSCH-TBSs-HS-SCCHless	INTEGER ::= 4
maxNrOfHS-DSCH-TBSs				INTEGER ::= 90
maxNrOfEHICHCodes				INTEGER ::= 4
maxNrOfE-PUCHSlotsLCR			INTEGER ::= 5
maxNrOfEPUCHcodes				INTEGER ::= 16
maxNrOfEHICHs					INTEGER ::= 32
maxNrOfCommonMACFlows			INTEGER ::= 8
maxNrOfCommonMACFlows-1			INTEGER ::= 7
maxNrOfPagingMACFlow			INTEGER ::= 4 
maxNrOfPagingMACFlow-1			INTEGER ::= 3
maxNrOfcommonMACQueues			INTEGER ::= 8
maxNrOfpagingMACQueues			INTEGER ::= 8
maxNrOfHS-DSCHTBSsE-PCH			INTEGER ::= 2
maxGANSSSat						INTEGER ::= 64
maxNoGANSS						INTEGER ::= 8
maxSgnType						INTEGER ::= 8
maxFrequencyinCell				INTEGER ::= 12
maxFrequencyinCell-1			INTEGER ::= 11
maxHSDPAFrequency				INTEGER ::= 8
maxHSDPAFrequency-1				INTEGER ::= 7
maxNrOfHSSCCHsinExt				INTEGER ::= 224
maxGANSSSatAlmanac				INTEGER ::= 36
maxGANSSClockMod				INTEGER ::= 4


-- **************************************************************
--
-- IEs
--
-- **************************************************************

id-AICH-Information													ProtocolIE-ID ::= 0
id-AICH-InformationItem-ResourceStatusInd							ProtocolIE-ID ::= 1
id-BCH-Information													ProtocolIE-ID ::= 7
id-BCH-InformationItem-ResourceStatusInd							ProtocolIE-ID ::= 8
id-BCCH-ModificationTime											ProtocolIE-ID ::= 9
id-BlockingPriorityIndicator										ProtocolIE-ID ::= 10
id-Cause															ProtocolIE-ID ::= 13
id-CCP-InformationItem-AuditRsp										ProtocolIE-ID ::= 14
id-CCP-InformationList-AuditRsp										ProtocolIE-ID ::= 15
id-CCP-InformationItem-ResourceStatusInd							ProtocolIE-ID ::= 16
id-Cell-InformationItem-AuditRsp									ProtocolIE-ID ::= 17
id-Cell-InformationItem-ResourceStatusInd							ProtocolIE-ID ::= 18
id-Cell-InformationList-AuditRsp									ProtocolIE-ID ::= 19
id-CellParameterID													ProtocolIE-ID ::= 23
id-CFN																ProtocolIE-ID ::= 24
id-C-ID																	ProtocolIE-ID ::= 25
id-CommonMeasurementAccuracy										ProtocolIE-ID ::= 39
id-CommonMeasurementObjectType-CM-Rprt								ProtocolIE-ID ::= 31
id-CommonMeasurementObjectType-CM-Rqst								ProtocolIE-ID ::= 32
id-CommonMeasurementObjectType-CM-Rsp								ProtocolIE-ID ::= 33
id-CommonMeasurementType											ProtocolIE-ID ::= 34
id-CommonPhysicalChannelID											ProtocolIE-ID ::= 35
id-CommonPhysicalChannelType-CTCH-SetupRqstFDD						ProtocolIE-ID ::= 36
id-CommonPhysicalChannelType-CTCH-SetupRqstTDD						ProtocolIE-ID ::= 37
id-CommunicationControlPortID										ProtocolIE-ID ::= 40
id-ConfigurationGenerationID										ProtocolIE-ID ::= 43
id-CRNC-CommunicationContextID										ProtocolIE-ID ::= 44
id-CriticalityDiagnostics											ProtocolIE-ID ::= 45
id-DCHs-to-Add-FDD													ProtocolIE-ID ::= 48
id-DCH-AddList-RL-ReconfPrepTDD										ProtocolIE-ID ::= 49
id-DCHs-to-Add-TDD													ProtocolIE-ID ::= 50
id-DCH-DeleteList-RL-ReconfPrepFDD									ProtocolIE-ID ::= 52
id-DCH-DeleteList-RL-ReconfPrepTDD									ProtocolIE-ID ::= 53
id-DCH-DeleteList-RL-ReconfRqstFDD									ProtocolIE-ID ::= 54
id-DCH-DeleteList-RL-ReconfRqstTDD									ProtocolIE-ID ::= 55
id-DCH-FDD-Information												ProtocolIE-ID ::= 56
id-DCH-TDD-Information												ProtocolIE-ID ::= 57
id-DCH-InformationResponse											ProtocolIE-ID ::= 59
id-FDD-DCHs-to-Modify												ProtocolIE-ID ::= 62
id-TDD-DCHs-to-Modify												ProtocolIE-ID ::= 63
id-DCH-ModifyList-RL-ReconfRqstTDD									ProtocolIE-ID ::= 65
id-DCH-RearrangeList-Bearer-RearrangeInd							ProtocolIE-ID ::= 135
id-DedicatedMeasurementObjectType-DM-Rprt							ProtocolIE-ID ::= 67
id-DedicatedMeasurementObjectType-DM-Rqst							ProtocolIE-ID ::= 68
id-DedicatedMeasurementObjectType-DM-Rsp							ProtocolIE-ID ::= 69
id-DedicatedMeasurementType											ProtocolIE-ID ::= 70
id-DL-CCTrCH-InformationItem-RL-SetupRqstTDD						ProtocolIE-ID ::= 72
id-DL-CCTrCH-InformationList-RL-AdditionRqstTDD						ProtocolIE-ID ::= 73
id-DL-CCTrCH-InformationList-RL-SetupRqstTDD						ProtocolIE-ID ::= 76
id-DL-DPCH-InformationItem-RL-AdditionRqstTDD						ProtocolIE-ID ::= 77
id-DL-DPCH-InformationList-RL-SetupRqstTDD							ProtocolIE-ID ::= 79
id-DL-DPCH-Information-RL-ReconfPrepFDD								ProtocolIE-ID ::= 81
id-DL-DPCH-Information-RL-ReconfRqstFDD								ProtocolIE-ID ::= 82
id-DL-DPCH-Information-RL-SetupRqstFDD								ProtocolIE-ID ::= 83
id-DL-DPCH-TimingAdjustment											ProtocolIE-ID ::= 21
id-DL-ReferencePowerInformationItem-DL-PC-Rqst						ProtocolIE-ID ::= 84
id-DLReferencePower													ProtocolIE-ID ::= 85
id-DLReferencePowerList-DL-PC-Rqst									ProtocolIE-ID ::= 86
id-Unused-ProtocolIE-ID-87											ProtocolIE-ID ::= 87
id-Unused-ProtocolIE-ID-89											ProtocolIE-ID ::= 89
id-Unused-ProtocolIE-ID-91											ProtocolIE-ID ::= 91
id-Unused-ProtocolIE-ID-93											ProtocolIE-ID ::= 93
id-DSCHs-to-Add-TDD													ProtocolIE-ID ::= 96
id-DSCH-Information-DeleteList-RL-ReconfPrepTDD						ProtocolIE-ID ::= 98
id-DSCH-Information-ModifyList-RL-ReconfPrepTDD						ProtocolIE-ID ::= 100
id-DSCH-InformationResponse											ProtocolIE-ID ::= 105
id-Unused-ProtocolIE-ID-106											ProtocolIE-ID ::= 106
id-DSCH-TDD-Information												ProtocolIE-ID ::= 107
id-Unused-ProtocolIE-ID-108											ProtocolIE-ID ::= 108
id-Unused-ProtocolIE-ID-112											ProtocolIE-ID ::= 112
id-DSCH-RearrangeList-Bearer-RearrangeInd							ProtocolIE-ID ::= 136
id-End-Of-Audit-Sequence-Indicator 									ProtocolIE-ID ::= 113
id-FACH-Information													ProtocolIE-ID ::= 116
id-FACH-InformationItem-ResourceStatusInd							ProtocolIE-ID ::= 117
id-FACH-ParametersList-CTCH-ReconfRqstTDD							ProtocolIE-ID ::= 120
id-FACH-ParametersListIE-CTCH-SetupRqstFDD							ProtocolIE-ID ::= 121
id-FACH-ParametersListIE-CTCH-SetupRqstTDD							ProtocolIE-ID ::= 122
id-IndicationType-ResourceStatusInd									ProtocolIE-ID ::= 123
id-Local-Cell-ID													ProtocolIE-ID ::= 124
id-Local-Cell-Group-InformationItem-AuditRsp						ProtocolIE-ID ::= 2
id-Local-Cell-Group-InformationItem-ResourceStatusInd				ProtocolIE-ID ::= 3
id-Local-Cell-Group-InformationItem2-ResourceStatusInd				ProtocolIE-ID ::= 4
id-Local-Cell-Group-InformationList-AuditRsp						ProtocolIE-ID ::= 5
id-Local-Cell-InformationItem-AuditRsp								ProtocolIE-ID ::= 125
id-Local-Cell-InformationItem-ResourceStatusInd						ProtocolIE-ID ::= 126
id-Local-Cell-InformationItem2-ResourceStatusInd					ProtocolIE-ID ::= 127
id-Local-Cell-InformationList-AuditRsp								ProtocolIE-ID ::= 128
id-AdjustmentPeriod													ProtocolIE-ID ::= 129
id-MaxAdjustmentStep												ProtocolIE-ID ::= 130
id-MaximumTransmissionPower											ProtocolIE-ID ::= 131
id-MeasurementFilterCoefficient										ProtocolIE-ID ::= 132
id-MeasurementID													ProtocolIE-ID ::= 133
id-MessageStructure													ProtocolIE-ID ::= 115
id-MIB-SB-SIB-InformationList-SystemInfoUpdateRqst					ProtocolIE-ID ::= 134
id-NodeB-CommunicationContextID										ProtocolIE-ID ::= 143
id-NeighbouringCellMeasurementInformation							ProtocolIE-ID ::= 455
id-P-CCPCH-Information												ProtocolIE-ID ::= 144
id-P-CCPCH-InformationItem-ResourceStatusInd						ProtocolIE-ID ::= 145
id-P-CPICH-Information												ProtocolIE-ID ::= 146
id-P-CPICH-InformationItem-ResourceStatusInd						ProtocolIE-ID ::= 147
id-P-SCH-Information												ProtocolIE-ID ::= 148
id-PCCPCH-Information-Cell-ReconfRqstTDD							ProtocolIE-ID ::= 150
id-PCCPCH-Information-Cell-SetupRqstTDD								ProtocolIE-ID ::= 151
id-PCH-Parameters-CTCH-ReconfRqstTDD								ProtocolIE-ID ::= 155
id-PCH-ParametersItem-CTCH-SetupRqstFDD								ProtocolIE-ID ::= 156
id-PCH-ParametersItem-CTCH-SetupRqstTDD								ProtocolIE-ID ::= 157
id-PCH-Information													ProtocolIE-ID ::= 158
id-PDSCH-Information-AddListIE-PSCH-ReconfRqst						ProtocolIE-ID ::= 161
id-PDSCH-Information-ModifyListIE-PSCH-ReconfRqst					ProtocolIE-ID ::= 162
id-PDSCHSets-AddList-PSCH-ReconfRqst								ProtocolIE-ID ::= 163
id-PDSCHSets-DeleteList-PSCH-ReconfRqst								ProtocolIE-ID ::= 164
id-PDSCHSets-ModifyList-PSCH-ReconfRqst								ProtocolIE-ID ::= 165
id-PICH-Information													ProtocolIE-ID ::= 166
id-PICH-Parameters-CTCH-ReconfRqstTDD								ProtocolIE-ID ::= 168
id-PowerAdjustmentType												ProtocolIE-ID ::= 169
id-PRACH-Information												ProtocolIE-ID ::= 170
id-PrimaryCCPCH-Information-Cell-ReconfRqstFDD						ProtocolIE-ID ::= 175
id-PrimaryCCPCH-Information-Cell-SetupRqstFDD						ProtocolIE-ID ::= 176
id-PrimaryCPICH-Information-Cell-ReconfRqstFDD						ProtocolIE-ID ::= 177
id-PrimaryCPICH-Information-Cell-SetupRqstFDD						ProtocolIE-ID ::= 178
id-PrimarySCH-Information-Cell-ReconfRqstFDD						ProtocolIE-ID ::= 179
id-PrimarySCH-Information-Cell-SetupRqstFDD							ProtocolIE-ID ::= 180
id-PrimaryScramblingCode											ProtocolIE-ID ::= 181
id-SCH-Information-Cell-ReconfRqstTDD								ProtocolIE-ID ::= 183
id-SCH-Information-Cell-SetupRqstTDD								ProtocolIE-ID ::= 184
id-PUSCH-Information-AddListIE-PSCH-ReconfRqst						ProtocolIE-ID ::= 185
id-PUSCH-Information-ModifyListIE-PSCH-ReconfRqst					ProtocolIE-ID ::= 186
id-PUSCHSets-AddList-PSCH-ReconfRqst								ProtocolIE-ID ::= 187
id-PUSCHSets-DeleteList-PSCH-ReconfRqst								ProtocolIE-ID ::= 188
id-PUSCHSets-ModifyList-PSCH-ReconfRqst								ProtocolIE-ID ::= 189
id-RACH-Information													ProtocolIE-ID ::= 190
id-RACH-ParametersItem-CTCH-SetupRqstFDD							ProtocolIE-ID ::= 196
id-RACH-ParameterItem-CTCH-SetupRqstTDD								ProtocolIE-ID ::= 197
id-ReportCharacteristics											ProtocolIE-ID ::= 198
id-Reporting-Object-RL-FailureInd									ProtocolIE-ID ::= 199
id-Reporting-Object-RL-RestoreInd									ProtocolIE-ID ::= 200
id-RL-InformationItem-DM-Rprt										ProtocolIE-ID ::= 202
id-RL-InformationItem-DM-Rqst										ProtocolIE-ID ::= 203
id-RL-InformationItem-DM-Rsp										ProtocolIE-ID ::= 204
id-RL-InformationItem-RL-AdditionRqstFDD							ProtocolIE-ID ::= 205
id-RL-informationItem-RL-DeletionRqst								ProtocolIE-ID ::= 206
id-RL-InformationItem-RL-FailureInd									ProtocolIE-ID ::= 207
id-RL-InformationItem-RL-PreemptRequiredInd							ProtocolIE-ID ::= 286
id-RL-InformationItem-RL-ReconfPrepFDD								ProtocolIE-ID ::= 208
id-RL-InformationItem-RL-ReconfRqstFDD								ProtocolIE-ID ::= 209
id-RL-InformationItem-RL-RestoreInd									ProtocolIE-ID ::= 210
id-RL-InformationItem-RL-SetupRqstFDD								ProtocolIE-ID ::= 211
id-RL-InformationList-RL-AdditionRqstFDD							ProtocolIE-ID ::= 212
id-RL-informationList-RL-DeletionRqst								ProtocolIE-ID ::= 213
id-RL-InformationList-RL-PreemptRequiredInd							ProtocolIE-ID ::= 237
id-RL-InformationList-RL-ReconfPrepFDD								ProtocolIE-ID ::= 214
id-RL-InformationList-RL-ReconfRqstFDD								ProtocolIE-ID ::= 215
id-RL-InformationList-RL-SetupRqstFDD								ProtocolIE-ID ::= 216
id-RL-InformationResponseItem-RL-AdditionRspFDD						ProtocolIE-ID ::= 217
id-RL-InformationResponseItem-RL-ReconfReady						ProtocolIE-ID ::= 218
id-RL-InformationResponseItem-RL-ReconfRsp							ProtocolIE-ID ::= 219
id-RL-InformationResponseItem-RL-SetupRspFDD						ProtocolIE-ID ::= 220
id-RL-InformationResponseList-RL-AdditionRspFDD						ProtocolIE-ID ::= 221
id-RL-InformationResponseList-RL-ReconfReady						ProtocolIE-ID ::= 222
id-RL-InformationResponseList-RL-ReconfRsp							ProtocolIE-ID ::= 223
id-RL-InformationResponseList-RL-SetupRspFDD						ProtocolIE-ID ::= 224
id-RL-InformationResponse-RL-AdditionRspTDD							ProtocolIE-ID ::= 225
id-RL-InformationResponse-RL-SetupRspTDD							ProtocolIE-ID ::= 226
id-RL-Information-RL-AdditionRqstTDD								ProtocolIE-ID ::= 227
id-RL-Information-RL-ReconfRqstTDD									ProtocolIE-ID ::= 228
id-RL-Information-RL-ReconfPrepTDD									ProtocolIE-ID ::= 229
id-RL-Information-RL-SetupRqstTDD									ProtocolIE-ID ::= 230
id-RL-ReconfigurationFailureItem-RL-ReconfFailure					ProtocolIE-ID ::= 236
id-RL-Set-InformationItem-DM-Rprt									ProtocolIE-ID ::= 238
id-RL-Set-InformationItem-DM-Rsp									ProtocolIE-ID ::= 240
id-RL-Set-InformationItem-RL-FailureInd								ProtocolIE-ID ::= 241
id-RL-Set-InformationItem-RL-RestoreInd								ProtocolIE-ID ::= 242
id-S-CCPCH-Information												ProtocolIE-ID ::= 247
id-S-CPICH-Information												ProtocolIE-ID ::= 249
id-SCH-Information													ProtocolIE-ID ::= 251
id-S-SCH-Information												ProtocolIE-ID ::= 253
id-Secondary-CCPCHListIE-CTCH-ReconfRqstTDD							ProtocolIE-ID ::= 257
id-Secondary-CCPCH-parameterListIE-CTCH-SetupRqstTDD				ProtocolIE-ID ::= 258
id-Secondary-CCPCH-Parameters-CTCH-ReconfRqstTDD					ProtocolIE-ID ::= 259
id-SecondaryCPICH-InformationItem-Cell-ReconfRqstFDD				ProtocolIE-ID ::= 260
id-SecondaryCPICH-InformationItem-Cell-SetupRqstFDD					ProtocolIE-ID ::= 261
id-SecondaryCPICH-InformationList-Cell-ReconfRqstFDD				ProtocolIE-ID ::= 262
id-SecondaryCPICH-InformationList-Cell-SetupRqstFDD					ProtocolIE-ID ::= 263
id-SecondarySCH-Information-Cell-ReconfRqstFDD						ProtocolIE-ID ::= 264
id-SecondarySCH-Information-Cell-SetupRqstFDD						ProtocolIE-ID ::= 265
id-SegmentInformationListIE-SystemInfoUpdate						ProtocolIE-ID ::= 266
id-SFN																ProtocolIE-ID ::= 268
id-SignallingBearerRequestIndicator									ProtocolIE-ID ::= 138
id-ShutdownTimer													ProtocolIE-ID ::= 269
id-Start-Of-Audit-Sequence-Indicator								ProtocolIE-ID ::= 114
id-Successful-RL-InformationRespItem-RL-AdditionFailureFDD			ProtocolIE-ID ::= 270
id-Successful-RL-InformationRespItem-RL-SetupFailureFDD				ProtocolIE-ID ::= 271
id-SyncCase															ProtocolIE-ID ::= 274
id-SyncCaseIndicatorItem-Cell-SetupRqstTDD-PSCH						ProtocolIE-ID ::= 275
id-T-Cell															ProtocolIE-ID ::= 276
id-TargetCommunicationControlPortID									ProtocolIE-ID ::= 139
id-TimeSlotConfigurationList-Cell-ReconfRqstTDD						ProtocolIE-ID ::= 277
id-TimeSlotConfigurationList-Cell-SetupRqstTDD						ProtocolIE-ID ::= 278
id-TransmissionDiversityApplied										ProtocolIE-ID ::= 279
id-TypeOfError														ProtocolIE-ID ::= 508
id-UARFCNforNt														ProtocolIE-ID ::= 280
id-UARFCNforNd														ProtocolIE-ID ::= 281
id-UARFCNforNu														ProtocolIE-ID ::= 282
id-UL-CCTrCH-InformationItem-RL-SetupRqstTDD						ProtocolIE-ID ::= 284
id-UL-CCTrCH-InformationList-RL-AdditionRqstTDD						ProtocolIE-ID ::= 285
id-UL-CCTrCH-InformationList-RL-SetupRqstTDD						ProtocolIE-ID ::= 288
id-UL-DPCH-InformationItem-RL-AdditionRqstTDD						ProtocolIE-ID ::= 289
id-UL-DPCH-InformationList-RL-SetupRqstTDD							ProtocolIE-ID ::= 291
id-UL-DPCH-Information-RL-ReconfPrepFDD								ProtocolIE-ID ::= 293
id-UL-DPCH-Information-RL-ReconfRqstFDD								ProtocolIE-ID ::= 294
id-UL-DPCH-Information-RL-SetupRqstFDD								ProtocolIE-ID ::= 295
id-Unsuccessful-RL-InformationRespItem-RL-AdditionFailureFDD		ProtocolIE-ID ::= 296
id-Unsuccessful-RL-InformationRespItem-RL-SetupFailureFDD			ProtocolIE-ID ::= 297
id-Unsuccessful-RL-InformationResp-RL-AdditionFailureTDD			ProtocolIE-ID ::= 300
id-Unsuccessful-RL-InformationResp-RL-SetupFailureTDD				ProtocolIE-ID ::= 301
id-USCH-Information-Add												ProtocolIE-ID ::= 302
id-USCH-Information-DeleteList-RL-ReconfPrepTDD						ProtocolIE-ID ::= 304
id-USCH-Information-ModifyList-RL-ReconfPrepTDD						ProtocolIE-ID ::= 306
id-USCH-InformationResponse											ProtocolIE-ID ::= 309
id-USCH-Information													ProtocolIE-ID ::= 310
id-USCH-RearrangeList-Bearer-RearrangeInd							ProtocolIE-ID ::= 141
id-Active-Pattern-Sequence-Information 								ProtocolIE-ID ::= 315
id-AICH-ParametersListIE-CTCH-ReconfRqstFDD							ProtocolIE-ID ::= 316
id-AdjustmentRatio													ProtocolIE-ID ::= 317
id-Not-Used-320														ProtocolIE-ID ::= 320
id-Not-Used-322														ProtocolIE-ID ::= 322
id-FACH-ParametersListIE-CTCH-ReconfRqstFDD							ProtocolIE-ID ::= 323
id-CauseLevel-PSCH-ReconfFailure									ProtocolIE-ID ::= 324
id-CauseLevel-RL-AdditionFailureFDD									ProtocolIE-ID ::= 325
id-CauseLevel-RL-AdditionFailureTDD									ProtocolIE-ID ::= 326
id-CauseLevel-RL-ReconfFailure										ProtocolIE-ID ::= 327
id-CauseLevel-RL-SetupFailureFDD									ProtocolIE-ID ::= 328
id-CauseLevel-RL-SetupFailureTDD									ProtocolIE-ID ::= 329
id-Not-Used-330														ProtocolIE-ID ::= 330
id-Not-Used-332														ProtocolIE-ID ::= 332
id-Closed-Loop-Timing-Adjustment-Mode								ProtocolIE-ID ::= 333
id-CommonPhysicalChannelType-CTCH-ReconfRqstFDD						ProtocolIE-ID ::= 334
id-Compressed-Mode-Deactivation-Flag								ProtocolIE-ID ::= 335
id-Not-Used-336														ProtocolIE-ID ::= 336
id-Not-Used-342														ProtocolIE-ID ::= 342
id-Not-Used-343														ProtocolIE-ID ::= 343
id-DL-CCTrCH-InformationAddList-RL-ReconfPrepTDD					ProtocolIE-ID ::= 346
id-DL-CCTrCH-InformationDeleteItem-RL-ReconfRqstTDD					ProtocolIE-ID ::= 347
id-DL-CCTrCH-InformationDeleteList-RL-ReconfPrepTDD					ProtocolIE-ID ::= 348
id-DL-CCTrCH-InformationDeleteList-RL-ReconfRqstTDD					ProtocolIE-ID ::= 349
id-DL-CCTrCH-InformationModifyItem-RL-ReconfRqstTDD					ProtocolIE-ID ::= 350
id-DL-CCTrCH-InformationModifyList-RL-ReconfPrepTDD					ProtocolIE-ID ::= 351
id-DL-CCTrCH-InformationModifyList-RL-ReconfRqstTDD					ProtocolIE-ID ::= 352
id-DL-DPCH-InformationAddListIE-RL-ReconfPrepTDD					ProtocolIE-ID ::= 353
id-DL-DPCH-InformationModify-AddListIE-RL-ReconfPrepTDD				ProtocolIE-ID ::= 355
id-DL-DPCH-InformationModify-DeleteListIE-RL-ReconfPrepTDD			ProtocolIE-ID ::= 356
id-DL-DPCH-InformationModify-ModifyListIE-RL-ReconfPrepTDD			ProtocolIE-ID ::= 357
id-DL-TPC-Pattern01Count 											ProtocolIE-ID ::= 358
id-DPC-Mode															ProtocolIE-ID ::= 450
id-DPCHConstant														ProtocolIE-ID ::= 359
id-Unused-ProtocolIE-ID-94											ProtocolIE-ID ::= 94
id-Unused-ProtocolIE-ID-110											ProtocolIE-ID ::= 110
id-Unused-ProtocolIE-ID-111											ProtocolIE-ID ::= 111
id-FACH-ParametersList-CTCH-SetupRsp								ProtocolIE-ID ::= 362
id-Limited-power-increase-information-Cell-SetupRqstFDD				ProtocolIE-ID ::= 369
id-PCH-Parameters-CTCH-SetupRsp										ProtocolIE-ID ::= 374
id-PCH-ParametersItem-CTCH-ReconfRqstFDD							ProtocolIE-ID ::= 375
id-Not-Used-376														ProtocolIE-ID ::= 376
id-PICH-ParametersItem-CTCH-ReconfRqstFDD							ProtocolIE-ID ::= 380
id-PRACHConstant													ProtocolIE-ID ::= 381
id-PRACH-ParametersListIE-CTCH-ReconfRqstFDD						ProtocolIE-ID ::= 383
id-PUSCHConstant													ProtocolIE-ID ::= 384
id-RACH-Parameters-CTCH-SetupRsp									ProtocolIE-ID ::= 385
id-Unused-ProtocolIE-ID-443											ProtocolIE-ID ::= 443
id-Synchronisation-Configuration-Cell-ReconfRqst					ProtocolIE-ID ::= 393
id-Synchronisation-Configuration-Cell-SetupRqst						ProtocolIE-ID ::= 394
id-Transmission-Gap-Pattern-Sequence-Information					ProtocolIE-ID ::= 395
id-UL-CCTrCH-InformationAddList-RL-ReconfPrepTDD					ProtocolIE-ID ::= 396
id-UL-CCTrCH-InformationDeleteItem-RL-ReconfRqstTDD					ProtocolIE-ID ::= 397
id-UL-CCTrCH-InformationDeleteList-RL-ReconfPrepTDD					ProtocolIE-ID ::= 398
id-UL-CCTrCH-InformationDeleteList-RL-ReconfRqstTDD					ProtocolIE-ID ::= 399
id-UL-CCTrCH-InformationModifyItem-RL-ReconfRqstTDD					ProtocolIE-ID ::= 400
id-UL-CCTrCH-InformationModifyList-RL-ReconfPrepTDD					ProtocolIE-ID ::= 401
id-UL-CCTrCH-InformationModifyList-RL-ReconfRqstTDD					ProtocolIE-ID ::= 402
id-UL-DPCH-InformationAddListIE-RL-ReconfPrepTDD					ProtocolIE-ID ::= 403
id-UL-DPCH-InformationModify-AddListIE-RL-ReconfPrepTDD				ProtocolIE-ID ::= 405
id-UL-DPCH-InformationModify-DeleteListIE-RL-ReconfPrepTDD			ProtocolIE-ID ::= 406
id-UL-DPCH-InformationModify-ModifyListIE-RL-ReconfPrepTDD			ProtocolIE-ID ::= 407
id-Unsuccessful-PDSCHSetItem-PSCH-ReconfFailureTDD					ProtocolIE-ID ::= 408
id-Unsuccessful-PUSCHSetItem-PSCH-ReconfFailureTDD					ProtocolIE-ID ::= 409
id-CommunicationContextInfoItem-Reset								ProtocolIE-ID ::= 412
id-CommunicationControlPortInfoItem-Reset							ProtocolIE-ID ::= 414
id-ResetIndicator													ProtocolIE-ID ::= 416
id-Unused-ProtocolIE-ID-417											ProtocolIE-ID ::= 417
id-Unused-ProtocolIE-ID-418											ProtocolIE-ID ::= 418
id-Unused-ProtocolIE-ID-419											ProtocolIE-ID ::= 419
id-Unused-ProtocolIE-ID-142											ProtocolIE-ID ::= 142
id-TimingAdvanceApplied												ProtocolIE-ID ::= 287
id-CFNReportingIndicator											ProtocolIE-ID ::= 6
id-SFNReportingIndicator											ProtocolIE-ID ::= 11
id-InnerLoopDLPCStatus												ProtocolIE-ID ::= 12
id-TimeslotISCPInfo													ProtocolIE-ID ::= 283
id-PICH-ParametersItem-CTCH-SetupRqstTDD							ProtocolIE-ID ::= 167
id-PRACH-ParametersItem-CTCH-SetupRqstTDD							ProtocolIE-ID ::= 20
id-CCTrCH-InformationItem-RL-FailureInd								ProtocolIE-ID ::= 46
id-CCTrCH-InformationItem-RL-RestoreInd								ProtocolIE-ID ::= 47
id-CauseLevel-SyncAdjustmntFailureTDD								ProtocolIE-ID ::= 420
id-CellAdjustmentInfo-SyncAdjustmntRqstTDD							ProtocolIE-ID ::= 421
id-CellAdjustmentInfoItem-SyncAdjustmentRqstTDD						ProtocolIE-ID ::= 494
id-CellSyncBurstInfoList-CellSyncReconfRqstTDD						ProtocolIE-ID ::= 482
id-CellSyncBurstTransInit-CellSyncInitiationRqstTDD					ProtocolIE-ID ::= 422
id-CellSyncBurstMeasureInit-CellSyncInitiationRqstTDD				ProtocolIE-ID ::= 423
id-CellSyncBurstTransReconfiguration-CellSyncReconfRqstTDD			ProtocolIE-ID ::= 424
id-CellSyncBurstMeasReconfiguration-CellSyncReconfRqstTDD			ProtocolIE-ID ::= 425
id-CellSyncBurstTransInfoList-CellSyncReconfRqstTDD					ProtocolIE-ID ::= 426
id-CellSyncBurstMeasInfoList-CellSyncReconfRqstTDD					ProtocolIE-ID ::= 427
id-CellSyncBurstTransReconfInfo-CellSyncReconfRqstTDD				ProtocolIE-ID ::= 428
id-CellSyncInfo-CellSyncReprtTDD									ProtocolIE-ID ::= 429
id-CSBTransmissionID												ProtocolIE-ID ::= 430
id-CSBMeasurementID													ProtocolIE-ID ::= 431
id-IntStdPhCellSyncInfoItem-CellSyncReprtTDD						ProtocolIE-ID ::= 432
id-NCyclesPerSFNperiod 												ProtocolIE-ID ::= 433
id-NRepetitionsPerCyclePeriod										ProtocolIE-ID ::= 434
id-SyncFrameNumber													ProtocolIE-ID ::= 437
id-SynchronisationReportType										ProtocolIE-ID ::= 438
id-SynchronisationReportCharacteristics								ProtocolIE-ID ::= 439
id-Unsuccessful-cell-InformationRespItem-SyncAdjustmntFailureTDD	ProtocolIE-ID ::= 440
id-LateEntranceCellSyncInfoItem-CellSyncReprtTDD					ProtocolIE-ID ::= 119
id-ReferenceClockAvailability										ProtocolIE-ID ::= 435
id-ReferenceSFNoffset												ProtocolIE-ID ::= 436
id-InformationExchangeID											ProtocolIE-ID ::= 444
id-InformationExchangeObjectType-InfEx-Rqst							ProtocolIE-ID ::= 445
id-InformationType													ProtocolIE-ID ::= 446
id-InformationReportCharacteristics									ProtocolIE-ID ::= 447
id-InformationExchangeObjectType-InfEx-Rsp							ProtocolIE-ID ::= 448
id-InformationExchangeObjectType-InfEx-Rprt							ProtocolIE-ID ::= 449
id-IPDLParameter-Information-Cell-ReconfRqstFDD						ProtocolIE-ID ::= 451
id-IPDLParameter-Information-Cell-SetupRqstFDD						ProtocolIE-ID ::= 452
id-IPDLParameter-Information-Cell-ReconfRqstTDD						ProtocolIE-ID ::= 453
id-IPDLParameter-Information-Cell-SetupRqstTDD						ProtocolIE-ID ::= 454
id-DL-DPCH-LCR-Information-RL-SetupRqstTDD							ProtocolIE-ID ::= 74
id-DwPCH-LCR-Information											ProtocolIE-ID ::= 78
id-DwPCH-LCR-InformationList-AuditRsp                   			ProtocolIE-ID ::= 90
id-DwPCH-LCR-Information-Cell-SetupRqstTDD                   		ProtocolIE-ID ::= 97
id-DwPCH-LCR-Information-Cell-ReconfRqstTDD							ProtocolIE-ID ::= 99
id-DwPCH-LCR-Information-ResourceStatusInd							ProtocolIE-ID ::= 101
id-maxFACH-Power-LCR-CTCH-SetupRqstTDD                   			ProtocolIE-ID ::= 154
id-maxFACH-Power-LCR-CTCH-ReconfRqstTDD                   			ProtocolIE-ID ::= 174
id-FPACH-LCR-Information											ProtocolIE-ID ::= 290
id-FPACH-LCR-Information-AuditRsp                   				ProtocolIE-ID ::= 292
id-FPACH-LCR-InformationList-AuditRsp                   			ProtocolIE-ID ::= 22
id-FPACH-LCR-InformationList-ResourceStatusInd                   	ProtocolIE-ID ::= 311
id-FPACH-LCR-Parameters-CTCH-SetupRqstTDD                   		ProtocolIE-ID ::= 312
id-FPACH-LCR-Parameters-CTCH-ReconfRqstTDD                   		ProtocolIE-ID ::= 314
id-PCCPCH-LCR-Information-Cell-SetupRqstTDD                   		ProtocolIE-ID ::= 456
id-PCH-Power-LCR-CTCH-SetupRqstTDD									ProtocolIE-ID ::= 457
id-PCH-Power-LCR-CTCH-ReconfRqstTDD									ProtocolIE-ID ::= 458
id-PICH-LCR-Parameters-CTCH-SetupRqstTDD                   			ProtocolIE-ID ::= 459
id-PRACH-LCR-ParametersList-CTCH-SetupRqstTDD                  		ProtocolIE-ID ::= 461
id-RL-InformationResponse-LCR-RL-SetupRspTDD	                   	ProtocolIE-ID ::= 463
id-Secondary-CCPCH-LCR-parameterList-CTCH-SetupRqstTDD              ProtocolIE-ID ::= 465
id-TimeSlot															ProtocolIE-ID ::= 495
id-TimeSlotConfigurationList-LCR-Cell-ReconfRqstTDD                 ProtocolIE-ID ::= 466
id-TimeSlotConfigurationList-LCR-Cell-SetupRqstTDD                  ProtocolIE-ID ::= 467
id-TimeslotISCP-LCR-InfoList-RL-SetupRqstTDD                   		ProtocolIE-ID ::= 468
id-TimeSlotLCR-CM-Rqst                   							ProtocolIE-ID ::= 469
id-UL-DPCH-LCR-Information-RL-SetupRqstTDD                   		ProtocolIE-ID ::= 470
id-DL-DPCH-InformationItem-LCR-RL-AdditionRqstTDD					ProtocolIE-ID ::= 472
id-UL-DPCH-InformationItem-LCR-RL-AdditionRqstTDD					ProtocolIE-ID ::= 473
id-TimeslotISCP-InformationList-LCR-RL-AdditionRqstTDD				ProtocolIE-ID ::= 474
id-DL-DPCH-LCR-InformationAddList-RL-ReconfPrepTDD					ProtocolIE-ID ::= 475
id-DL-DPCH-LCR-InformationModify-AddList-RL-ReconfPrepTDD			ProtocolIE-ID ::= 477
id-DL-Timeslot-LCR-InformationModify-ModifyList-RL-ReconfPrepTDD	ProtocolIE-ID ::= 479
id-TimeslotISCPInfoList-LCR-DL-PC-RqstTDD							ProtocolIE-ID ::= 480
id-UL-DPCH-LCR-InformationAddListIE-RL-ReconfPrepTDD				ProtocolIE-ID ::= 481
id-UL-DPCH-LCR-InformationModify-AddList							ProtocolIE-ID ::= 483
id-UL-TimeslotLCR-Information-RL-ReconfPrepTDD						ProtocolIE-ID ::= 485
id-UL-SIRTarget														ProtocolIE-ID ::= 510
id-PDSCH-AddInformation-LCR-PSCH-ReconfRqst							ProtocolIE-ID ::= 486
id-PDSCH-AddInformation-LCR-AddListIE-PSCH-ReconfRqst				ProtocolIE-ID ::= 487
id-Unused-ProtocolIE-ID-26											ProtocolIE-ID ::=  26
id-Unused-ProtocolIE-ID-27											ProtocolIE-ID ::=  27
id-PDSCH-ModifyInformation-LCR-PSCH-ReconfRqst						ProtocolIE-ID ::= 488
id-PDSCH-ModifyInformation-LCR-ModifyListIE-PSCH-ReconfRqst			ProtocolIE-ID ::= 489
id-PUSCH-AddInformation-LCR-PSCH-ReconfRqst							ProtocolIE-ID ::= 490
id-PUSCH-AddInformation-LCR-AddListIE-PSCH-ReconfRqst				ProtocolIE-ID ::= 491
id-PUSCH-ModifyInformation-LCR-PSCH-ReconfRqst						ProtocolIE-ID ::= 492
id-PUSCH-ModifyInformation-LCR-ModifyListIE-PSCH-ReconfRqst			ProtocolIE-ID ::= 493
id-timeslotInfo-CellSyncInitiationRqstTDD							ProtocolIE-ID ::= 496
id-SyncReportType-CellSyncReprtTDD									ProtocolIE-ID ::= 497
id-Power-Local-Cell-Group-InformationItem-AuditRsp					ProtocolIE-ID ::= 498
id-Power-Local-Cell-Group-InformationItem-ResourceStatusInd			ProtocolIE-ID ::= 499
id-Power-Local-Cell-Group-InformationItem2-ResourceStatusInd		ProtocolIE-ID ::= 500
id-Power-Local-Cell-Group-InformationList-AuditRsp					ProtocolIE-ID ::= 501
id-Power-Local-Cell-Group-InformationList-ResourceStatusInd			ProtocolIE-ID ::= 502
id-Power-Local-Cell-Group-InformationList2-ResourceStatusInd		ProtocolIE-ID ::= 503
id-Power-Local-Cell-Group-ID										ProtocolIE-ID ::= 504
id-PUSCH-Info-DM-Rqst												ProtocolIE-ID ::= 505
id-PUSCH-Info-DM-Rsp												ProtocolIE-ID ::= 506
id-PUSCH-Info-DM-Rprt												ProtocolIE-ID ::= 507
id-InitDL-Power														ProtocolIE-ID ::= 509
id-cellSyncBurstRepetitionPeriod									ProtocolIE-ID ::= 511
id-ReportCharacteristicsType-OnModification							ProtocolIE-ID ::= 512
id-SFNSFNMeasurementValueInformation								ProtocolIE-ID ::= 513
id-SFNSFNMeasurementThresholdInformation							ProtocolIE-ID ::= 514
id-TUTRANGPSMeasurementValueInformation								ProtocolIE-ID ::= 515
id-TUTRANGPSMeasurementThresholdInformation							ProtocolIE-ID ::= 516
id-Rx-Timing-Deviation-Value-LCR									ProtocolIE-ID ::= 520
id-RL-InformationResponse-LCR-RL-AdditionRspTDD						ProtocolIE-ID ::= 51
id-DL-PowerBalancing-Information									ProtocolIE-ID ::= 28
id-DL-PowerBalancing-ActivationIndicator							ProtocolIE-ID ::= 29
id-DL-PowerBalancing-UpdatedIndicator								ProtocolIE-ID ::= 30
id-CCTrCH-Initial-DL-Power-RL-SetupRqstTDD							ProtocolIE-ID ::= 517
id-CCTrCH-Initial-DL-Power-RL-AdditionRqstTDD						ProtocolIE-ID ::= 518
id-CCTrCH-Initial-DL-Power-RL-ReconfPrepTDD							ProtocolIE-ID ::= 519
id-IPDLParameter-Information-LCR-Cell-SetupRqstTDD					ProtocolIE-ID ::= 41
id-IPDLParameter-Information-LCR-Cell-ReconfRqstTDD 				ProtocolIE-ID ::= 42
id-HS-PDSCH-HS-SCCH-E-AGCH-E-RGCH-E-HICH-MaxPower-PSCH-ReconfRqst	ProtocolIE-ID ::= 522
id-HS-PDSCH-HS-SCCH-ScramblingCode-PSCH-ReconfRqst					ProtocolIE-ID ::= 523
id-HS-PDSCH-FDD-Code-Information-PSCH-ReconfRqst					ProtocolIE-ID ::= 524
id-HS-SCCH-FDD-Code-Information-PSCH-ReconfRqst						ProtocolIE-ID ::= 525
id-HS-PDSCH-TDD-Information-PSCH-ReconfRqst							ProtocolIE-ID ::= 526
id-Add-To-HS-SCCH-Resource-Pool-PSCH-ReconfRqst						ProtocolIE-ID ::= 527
id-Modify-HS-SCCH-Resource-Pool-PSCH-ReconfRqst						ProtocolIE-ID ::= 528
id-Delete-From-HS-SCCH-Resource-Pool-PSCH-ReconfRqst				ProtocolIE-ID ::= 529
id-bindingID														ProtocolIE-ID ::= 102
id-RL-Specific-DCH-Info												ProtocolIE-ID ::= 103
id-transportlayeraddress 											ProtocolIE-ID ::= 104
id-DelayedActivation 												ProtocolIE-ID ::= 231
id-DelayedActivationList-RL-ActivationCmdFDD						ProtocolIE-ID ::= 232
id-DelayedActivationInformation-RL-ActivationCmdFDD					ProtocolIE-ID ::= 233
id-DelayedActivationList-RL-ActivationCmdTDD						ProtocolIE-ID ::= 234
id-DelayedActivationInformation-RL-ActivationCmdTDD					ProtocolIE-ID ::= 235
id-neighbouringTDDCellMeasurementInformationLCR						ProtocolIE-ID ::= 58
id-SYNCDlCodeId-TransInitLCR-CellSyncInitiationRqstTDD				ProtocolIE-ID ::= 543
id-SYNCDlCodeId-MeasureInitLCR-CellSyncInitiationRqstTDD			ProtocolIE-ID ::= 544
id-SYNCDlCodeIdTransReconfInfoLCR-CellSyncReconfRqstTDD				ProtocolIE-ID ::= 545
id-SYNCDlCodeIdMeasReconfigurationLCR-CellSyncReconfRqstTDD			ProtocolIE-ID ::= 546
id-SYNCDlCodeIdMeasInfoList-CellSyncReconfRqstTDD					ProtocolIE-ID ::= 547
id-SyncDLCodeIdsMeasInfoList-CellSyncReprtTDD						ProtocolIE-ID ::= 548
id-SyncDLCodeIdThreInfoLCR											ProtocolIE-ID ::= 549
id-NSubCyclesPerCyclePeriod-CellSyncReconfRqstTDD					ProtocolIE-ID ::= 550
id-DwPCH-Power														ProtocolIE-ID ::= 551
id-AccumulatedClockupdate-CellSyncReprtTDD							ProtocolIE-ID ::= 552
id-Angle-Of-Arrival-Value-LCR										ProtocolIE-ID ::= 521
id-HSDSCH-FDD-Information											ProtocolIE-ID ::= 530
id-HSDSCH-FDD-Information-Response									ProtocolIE-ID ::= 531
id-HSDSCH-Information-to-Modify										ProtocolIE-ID ::= 534
id-HSDSCH-RNTI														ProtocolIE-ID ::= 535
id-HSDSCH-TDD-Information											ProtocolIE-ID ::= 536
id-HSDSCH-TDD-Information-Response									ProtocolIE-ID ::= 537
id-HSPDSCH-RL-ID													ProtocolIE-ID ::= 541
id-PrimCCPCH-RSCP-DL-PC-RqstTDD										ProtocolIE-ID ::= 542
id-Unused-ProtocolIE-ID-64											ProtocolIE-ID ::= 64
id-PDSCH-RL-ID														ProtocolIE-ID ::= 66
id-HSDSCH-RearrangeList-Bearer-RearrangeInd							ProtocolIE-ID ::= 553
id-UL-Synchronisation-Parameters-LCR								ProtocolIE-ID ::= 554
id-HSDSCH-FDD-Update-Information									ProtocolIE-ID ::= 555
id-HSDSCH-TDD-Update-Information									ProtocolIE-ID ::= 556
id-DL-DPCH-TimeSlotFormat-LCR-ModifyItem-RL-ReconfPrepTDD			ProtocolIE-ID ::= 558
id-UL-DPCH-TimeSlotFormat-LCR-ModifyItem-RL-ReconfPrepTDD			ProtocolIE-ID ::= 559
id-TDD-TPC-UplinkStepSize-LCR-RL-SetupRqstTDD						ProtocolIE-ID ::= 560
id-TDD-TPC-UplinkStepSize-LCR-RL-AdditionRqstTDD					ProtocolIE-ID ::= 561
id-TDD-TPC-DownlinkStepSize-RL-AdditionRqstTDD						ProtocolIE-ID ::= 562
id-TDD-TPC-UplinkStepSize-InformationAdd-LCR-RL-ReconfPrepTDD		ProtocolIE-ID ::= 563
id-TDD-TPC-UplinkStepSize-InformationModify-LCR-RL-ReconfPrepTDD	ProtocolIE-ID ::= 564
id-TDD-TPC-DownlinkStepSize-InformationModify-RL-ReconfPrepTDD		ProtocolIE-ID ::= 565
id-TDD-TPC-DownlinkStepSize-InformationAdd-RL-ReconfPrepTDD		ProtocolIE-ID ::= 566
id-CCTrCH-Maximum-DL-Power-RL-SetupRqstTDD							ProtocolIE-ID ::= 567
id-CCTrCH-Minimum-DL-Power-RL-SetupRqstTDD							ProtocolIE-ID ::= 568
id-CCTrCH-Maximum-DL-Power-RL-AdditionRqstTDD						ProtocolIE-ID ::= 569
id-CCTrCH-Minimum-DL-Power-RL-AdditionRqstTDD						ProtocolIE-ID ::= 570
id-CCTrCH-Maximum-DL-Power-InformationAdd-RL-ReconfPrepTDD			ProtocolIE-ID ::= 571
id-CCTrCH-Minimum-DL-Power-InformationAdd-RL-ReconfPrepTDD			ProtocolIE-ID ::= 572
id-CCTrCH-Maximum-DL-Power-InformationModify-RL-ReconfPrepTDD		ProtocolIE-ID ::= 573
id-CCTrCH-Minimum-DL-Power-InformationModify-RL-ReconfPrepTDD		ProtocolIE-ID ::= 574
id-Maximum-DL-Power-Modify-LCR-InformationModify-RL-ReconfPrepTDD	ProtocolIE-ID ::= 575
id-Minimum-DL-Power-Modify-LCR-InformationModify-RL-ReconfPrepTDD	ProtocolIE-ID ::= 576
id-DL-DPCH-LCR-InformationModify-ModifyList-RL-ReconfRqstTDD		ProtocolIE-ID ::= 577
id-CCTrCH-Maximum-DL-Power-InformationModify-RL-ReconfRqstTDD		ProtocolIE-ID ::= 578
id-CCTrCH-Minimum-DL-Power-InformationModify-RL-ReconfRqstTDD		ProtocolIE-ID ::= 579
id-Initial-DL-Power-TimeslotLCR-InformationItem						ProtocolIE-ID ::= 580
id-Maximum-DL-Power-TimeslotLCR-InformationItem						ProtocolIE-ID ::= 581
id-Minimum-DL-Power-TimeslotLCR-InformationItem						ProtocolIE-ID ::= 582
id-HS-DSCHProvidedBitRateValueInformation							ProtocolIE-ID ::= 583
id-HS-DSCHRequiredPowerValueInformation								ProtocolIE-ID ::= 585
id-HS-DSCHRequiredPowerValue										ProtocolIE-ID ::= 586
id-TransmittedCarrierPowerOfAllCodesNotUsedForHSTransmission			ProtocolIE-ID ::= 587
id-HS-SICH-Reception-Quality 										ProtocolIE-ID ::= 588
id-HS-SICH-Reception-Quality-Measurement-Value 						ProtocolIE-ID ::= 589
id-HSSICH-Info-DM-Rprt 												ProtocolIE-ID ::= 590
id-HSSICH-Info-DM-Rqst												ProtocolIE-ID ::= 591
id-HSSICH-Info-DM-Rsp												ProtocolIE-ID ::= 592
id-Best-Cell-Portions-Value											ProtocolIE-ID ::= 593
id-Primary-CPICH-Usage-for-Channel-Estimation						ProtocolIE-ID ::= 594
id-Secondary-CPICH-Information-Change								ProtocolIE-ID ::= 595
id-NumberOfReportedCellPortions										ProtocolIE-ID ::= 596
id-CellPortion-InformationItem-Cell-SetupRqstFDD					ProtocolIE-ID ::= 597
id-CellPortion-InformationList-Cell-SetupRqstFDD					ProtocolIE-ID ::= 598
id-TimeslotISCP-LCR-InfoList-RL-ReconfPrepTDD						ProtocolIE-ID ::= 599
id-Secondary-CPICH-Information										ProtocolIE-ID ::= 600
id-Received-total-wide-band-power-For-CellPortion					ProtocolIE-ID ::= 601
id-Unidirectional-DCH-Indicator										ProtocolIE-ID ::= 602
id-TimingAdjustmentValueLCR											ProtocolIE-ID ::= 603
id-multipleRL-dl-DPCH-InformationList								ProtocolIE-ID ::= 604
id-multipleRL-dl-DPCH-InformationModifyList							ProtocolIE-ID ::= 605
id-multipleRL-ul-DPCH-InformationList								ProtocolIE-ID ::= 606
id-multipleRL-ul-DPCH-InformationModifyList							ProtocolIE-ID ::= 607
id-RL-ID															ProtocolIE-ID ::= 608
id-SAT-Info-Almanac-ExtItem											ProtocolIE-ID ::= 609
id-HSDPA-Capability													ProtocolIE-ID ::= 610
id-HSDSCH-Resources-Information-AuditRsp							ProtocolIE-ID ::= 611
id-HSDSCH-Resources-Information-ResourceStatusInd					ProtocolIE-ID ::= 612
id-HSDSCH-MACdFlows-to-Add											ProtocolIE-ID ::= 613
id-HSDSCH-MACdFlows-to-Delete										ProtocolIE-ID ::= 614
id-HSDSCH-Information-to-Modify-Unsynchronised						ProtocolIE-ID ::= 615
id-TnlQos															ProtocolIE-ID ::= 616
id-Received-total-wide-band-power-For-CellPortion-Value				ProtocolIE-ID ::= 617
id-Transmitted-Carrier-Power-For-CellPortion						ProtocolIE-ID ::= 618
id-Transmitted-Carrier-Power-For-CellPortion-Value 					ProtocolIE-ID ::= 619
id-TransmittedCarrierPowerOfAllCodesNotUsedForHS-PDSCH-HS-SCCH-E-AGCH-E-RGCHOrE-HICHTransmissionCellPortion		ProtocolIE-ID ::= 620
id-TransmittedCarrierPowerOfAllCodesNotUsedForHS-PDSCH-HS-SCCH-E-AGCH-E-RGCHOrE-HICHTransmissionCellPortionValue	ProtocolIE-ID ::= 621
id-UpPTSInterferenceValue											ProtocolIE-ID ::= 622
id-PrimaryCCPCH-RSCP-Delta											ProtocolIE-ID ::= 623
id-MeasurementRecoveryBehavior										ProtocolIE-ID ::= 624
id-MeasurementRecoveryReportingIndicator							ProtocolIE-ID ::= 625
id-MeasurementRecoverySupportIndicator								ProtocolIE-ID ::= 626
id-Tstd-indicator													ProtocolIE-ID ::= 627
id-multiple-RL-Information-RL-ReconfPrepTDD							ProtocolIE-ID ::= 628
id-multiple-RL-Information-RL-ReconfRqstTDD							ProtocolIE-ID ::= 629
id-DL-DPCH-Power-Information-RL-ReconfPrepFDD						ProtocolIE-ID ::= 630
id-F-DPCH-Information-RL-ReconfPrepFDD								ProtocolIE-ID ::= 631
id-F-DPCH-Information-RL-SetupRqstFDD								ProtocolIE-ID ::= 632
id-Additional-S-CCPCH-Parameters-CTCH-ReconfRqstTDD					ProtocolIE-ID ::= 633
id-Additional-S-CCPCH-Parameters-CTCH-SetupRqstTDD					ProtocolIE-ID ::= 634
id-Additional-S-CCPCH-LCR-Parameters-CTCH-ReconfRqstTDD				ProtocolIE-ID ::= 635
id-Additional-S-CCPCH-LCR-Parameters-CTCH-SetupRqstTDD				ProtocolIE-ID ::= 636
id-MICH-CFN															ProtocolIE-ID ::= 637
id-MICH-Information-AuditRsp										ProtocolIE-ID ::= 638
id-MICH-Information-ResourceStatusInd								ProtocolIE-ID ::= 639
id-MICH-Parameters-CTCH-ReconfRqstFDD								ProtocolIE-ID ::= 640
id-MICH-Parameters-CTCH-ReconfRqstTDD								ProtocolIE-ID ::= 641
id-MICH-Parameters-CTCH-SetupRqstFDD								ProtocolIE-ID ::= 642
id-MICH-Parameters-CTCH-SetupRqstTDD								ProtocolIE-ID ::= 643
id-Modification-Period												ProtocolIE-ID ::= 644
id-NI-Information-NotifUpdateCmd									ProtocolIE-ID ::= 645
id-S-CCPCH-InformationListExt-AuditRsp								ProtocolIE-ID ::= 646
id-S-CCPCH-InformationListExt-ResourceStatusInd						ProtocolIE-ID ::= 647
id-S-CCPCH-LCR-InformationListExt-AuditRsp							ProtocolIE-ID ::= 648
id-S-CCPCH-LCR-InformationListExt-ResourceStatusInd					ProtocolIE-ID ::= 649
id-HARQ-Preamble-Mode												ProtocolIE-ID ::= 650
id-Initial-DL-DPCH-TimingAdjustment									ProtocolIE-ID ::= 651
id-Initial-DL-DPCH-TimingAdjustment-Allowed							ProtocolIE-ID ::= 652
id-DLTransmissionBranchLoadValue									ProtocolIE-ID ::= 653
id-Power-Local-Cell-Group-choice-CM-Rqst							ProtocolIE-ID ::= 654
id-Power-Local-Cell-Group-choice-CM-Rsp								ProtocolIE-ID ::= 655
id-Power-Local-Cell-Group-choice-CM-Rprt							ProtocolIE-ID ::= 656
id-SynchronisationIndicator											ProtocolIE-ID ::= 657
id-HSDPA-And-EDCH-CellPortion-Information-PSCH-ReconfRqst			ProtocolIE-ID ::= 658
id-Unused-ProtocolIE-ID-659											ProtocolIE-ID ::= 659
id-HS-DSCHRequiredPowerValue-For-Cell-Portion						ProtocolIE-ID ::= 660
id-HS-DSCHRequiredPowerValueInformation-For-CellPortion				ProtocolIE-ID ::= 661
id-HS-DSCHProvidedBitRateValueInformation-For-CellPortion			ProtocolIE-ID ::= 662
id-E-AGCH-And-E-RGCH-E-HICH-FDD-Scrambling-Code						ProtocolIE-ID ::= 663
id-E-AGCH-FDD-Code-Information										ProtocolIE-ID ::= 664
id-E-DCH-Capability													ProtocolIE-ID ::= 665
id-E-DCH-FDD-DL-Control-Channel-Information							ProtocolIE-ID ::= 666
id-E-DCH-FDD-Information											ProtocolIE-ID ::= 667
id-E-DCH-FDD-Information-Response									ProtocolIE-ID ::= 668
id-E-DCH-FDD-Information-to-Modify									ProtocolIE-ID ::= 669
id-E-DCH-MACdFlows-to-Add											ProtocolIE-ID ::= 670
id-E-DCH-MACdFlows-to-Delete										ProtocolIE-ID ::= 671
id-E-DCH-Resources-Information-AuditRsp								ProtocolIE-ID ::= 672
id-E-DCH-Resources-Information-ResourceStatusInd					ProtocolIE-ID ::= 673
id-E-DCH-RL-Indication												ProtocolIE-ID ::= 674
id-E-DCH-RL-Set-ID													ProtocolIE-ID ::= 675
id-E-DPCH-Information-RL-ReconfPrepFDD								ProtocolIE-ID ::= 676
id-E-DPCH-Information-RL-SetupRqstFDD								ProtocolIE-ID ::= 677
id-E-RGCH-E-HICH-FDD-Code-Information								ProtocolIE-ID ::= 678
id-Serving-E-DCH-RL-ID												ProtocolIE-ID ::= 679
id-UL-DPDCH-Indicator-For-E-DCH-Operation							ProtocolIE-ID ::= 680
id-FDD-S-CCPCH-FrameOffset-CTCH-SetupRqstFDD						ProtocolIE-ID ::= 681
id-E-DPCH-Information-RL-ReconfRqstFDD								ProtocolIE-ID ::= 682
id-Maximum-Target-ReceivedTotalWideBandPower						ProtocolIE-ID ::= 683
id-E-DCHProvidedBitRateValueInformation								ProtocolIE-ID ::= 684
id-HARQ-Preamble-Mode-Activation-Indicator							ProtocolIE-ID ::= 685
id-RL-Specific-E-DCH-Info											ProtocolIE-ID ::= 686
id-E-DCH-CapacityConsumptionLaw										ProtocolIE-ID ::= 687
id-multiple-DedicatedMeasurementValueList-TDD-DM-Rsp				ProtocolIE-ID ::= 688
id-multiple-DedicatedMeasurementValueList-LCR-TDD-DM-Rsp			ProtocolIE-ID ::= 689
id-E-DCH-RearrangeList-Bearer-RearrangeInd							ProtocolIE-ID ::= 690
id-Unused-ProtocolIE-ID-691											ProtocolIE-ID ::= 691
id-multipleRL-dl-CCTrCH-InformationModifyList-RL-ReconfRqstTDD		ProtocolIE-ID ::= 692
id-Target-NonServing-EDCH-To-Total-EDCH-Power-Ratio					ProtocolIE-ID ::= 693
id-CellPortion-InformationItem-Cell-ReconfRqstFDD					ProtocolIE-ID ::= 694
id-CellPortion-InformationList-Cell-ReconfRqstFDD					ProtocolIE-ID ::= 695
id-multiple-PUSCH-InfoList-DM-Rsp									ProtocolIE-ID ::= 696
id-multiple-PUSCH-InfoList-DM-Rprt									ProtocolIE-ID ::= 697
id-Reference-ReceivedTotalWideBandPower								ProtocolIE-ID ::= 698
id-E-DCH-Serving-Cell-Change-Info-Response							ProtocolIE-ID ::= 699
id-HS-DSCH-Serving-Cell-Change-Info									ProtocolIE-ID ::= 700
id-HS-DSCH-Serving-Cell-Change-Info-Response						ProtocolIE-ID ::= 701
id-Serving-Cell-Change-CFN											ProtocolIE-ID ::= 702
id-E-DCH-HARQ-Combining-Capability									ProtocolIE-ID ::= 703
id-E-DCH-TTI2ms-Capability											ProtocolIE-ID ::= 704
id-E-DCH-SF-Capability												ProtocolIE-ID ::= 705
id-E-DCH-FDD-Update-Information										ProtocolIE-ID ::= 706
id-F-DPCH-Capability												ProtocolIE-ID ::= 707
id-E-DCH-Non-serving-Relative-Grant-Down-CommandsValue				ProtocolIE-ID ::= 708
id-HSSICH-SIRTarget													ProtocolIE-ID ::= 709
id-multiple-HSSICHMeasurementValueList-TDD-DM-Rsp					ProtocolIE-ID ::= 710
id-PLCCH-Information-AuditRsp 										ProtocolIE-ID ::= 711
id-PLCCH-Information-ResourceStatusInd								ProtocolIE-ID ::= 712
id-PLCCH-Information-RL-ReconfPrepTDDLCR							ProtocolIE-ID ::= 713
id-PLCCH-Information-UL-TimeslotLCR-Info							ProtocolIE-ID ::= 714
id-PLCCH-InformationList-AuditRsp									ProtocolIE-ID ::= 715
id-PLCCH-InformationList-ResourceStatusInd							ProtocolIE-ID ::= 716
id-PLCCH-Parameters-CTCH-ReconfRqstTDD								ProtocolIE-ID ::= 717
id-S-CCPCH-768-Parameters-CTCH-SetupRqstTDD							ProtocolIE-ID ::= 718
id-PICH-768-Parameters-CTCH-SetupRqstTDD							ProtocolIE-ID ::= 719
id-PRACH-768-Parameters-CTCH-SetupRqstTDD							ProtocolIE-ID ::= 720
id-S-CCPCH-768-Parameters-CTCH-ReconfRqstTDD						ProtocolIE-ID ::= 721
id-PICH-768-Parameters-CTCH-ReconfRqstTDD							ProtocolIE-ID ::= 722
id-MICH-768-Parameters-CTCH-ReconfRqstTDD							ProtocolIE-ID ::= 723
id-CommonPhysicalChannelID768-CommonTrChDeletionReq 				ProtocolIE-ID ::= 724
id-S-CCPCH-768-InformationList-AuditRsp								ProtocolIE-ID ::= 725
id-S-CCPCH-768-Information-AuditRsp 								ProtocolIE-ID ::= 726
id-neighbouringTDDCellMeasurementInformation768						ProtocolIE-ID ::= 727
id-PCCPCH-768-Information-Cell-SetupRqstTDD 						ProtocolIE-ID ::= 728
id-SCH-768-Information-Cell-SetupRqstTDD							ProtocolIE-ID ::= 729
id-SCH-768-Information-Cell-ReconfRqstTDD 							ProtocolIE-ID ::= 730
id-PCCPCH-768-Information-Cell-ReconfRqstTDD 						ProtocolIE-ID ::= 731
id-P-CCPCH-768-Information-AuditRsp									ProtocolIE-ID ::= 732
id-PICH-768-Information-AuditRsp									ProtocolIE-ID ::= 733
id-PRACH-768-InformationList-AuditRsp								ProtocolIE-ID ::= 734
id-SCH-768-Information-AuditRsp										ProtocolIE-ID ::= 735
id-MICH-768-Information-AuditRsp									ProtocolIE-ID ::= 736
id-PRACH-768-Information											ProtocolIE-ID ::= 737
id-S-CCPCH-768-Information-ResourceStatusInd						ProtocolIE-ID ::= 738
id-P-CCPCH-768-Information-ResourceStatusInd						ProtocolIE-ID ::= 739
id-PICH-768-Information-ResourceStatusInd							ProtocolIE-ID ::= 740
id-PRACH-768-InformationList-ResourceStatusInd						ProtocolIE-ID ::= 741
id-SCH-768-Information-ResourceStatusInd							ProtocolIE-ID ::= 742
id-MICH-768-Information-ResourceStatusInd							ProtocolIE-ID ::= 743
id-S-CCPCH-768-InformationList-ResourceStatusInd					ProtocolIE-ID ::= 744
id-UL-DPCH-768-Information-RL-SetupRqstTDD							ProtocolIE-ID ::= 745
id-DL-DPCH-768-Information-RL-SetupRqstTDD							ProtocolIE-ID ::= 746
id-DL-DPCH-InformationItem-768-RL-AdditionRqstTDD					ProtocolIE-ID ::= 747
id-UL-DPCH-InformationItem-768-RL-AdditionRqstTDD					ProtocolIE-ID ::= 748
id-UL-DPCH-768-InformationAddItemIE-RL-ReconfPrepTDD				ProtocolIE-ID ::= 749
id-UL-DPCH-768-InformationAddListIE-RL-ReconfPrepTDD				ProtocolIE-ID ::= 750
id-UL-DPCH-768-InformationModify-AddItem							ProtocolIE-ID ::= 751
id-UL-DPCH-768-InformationModify-AddList							ProtocolIE-ID ::= 752
id-UL-Timeslot768-Information-RL-ReconfPrepTDD						ProtocolIE-ID ::= 753
id-DL-DPCH-768-InformationAddItem-RL-ReconfPrepTDD					ProtocolIE-ID ::= 754
id-DL-DPCH-768-InformationAddList-RL-ReconfPrepTDD					ProtocolIE-ID ::= 755
id-DL-DPCH-768-InformationModify-AddItem-RL-ReconfPrepTDD			ProtocolIE-ID ::= 756
id-DL-DPCH-768-InformationModify-AddList-RL-ReconfPrepTDD			ProtocolIE-ID ::= 757
id-DL-Timeslot-768-InformationModify-ModifyList-RL-ReconfPrepTDD	ProtocolIE-ID ::= 758
id-DPCH-ID768-DM-Rqst												ProtocolIE-ID ::= 759
id-multiple-DedicatedMeasurementValueList-768-TDD-DM-Rsp			ProtocolIE-ID ::= 760
id-DPCH-ID768-DM-Rsp												ProtocolIE-ID ::= 761
id-Rx-Timing-Deviation-Value-768									ProtocolIE-ID ::= 762
id-DPCH-ID768-DM-Rprt												ProtocolIE-ID ::= 763
id-PDSCH-AddInformation-768-PSCH-ReconfRqst							ProtocolIE-ID ::= 764
id-PDSCH-ModifyInformation-768-PSCH-ReconfRqst						ProtocolIE-ID ::= 765
id-PUSCH-AddInformation-768-PSCH-ReconfRqst							ProtocolIE-ID ::= 766
id-PUSCH-ModifyInformation-768-PSCH-ReconfRqst						ProtocolIE-ID ::= 767
id-dL-HS-PDSCH-Timeslot-Information-768-PSCH-ReconfRqst				ProtocolIE-ID ::= 768
id-hS-SCCH-Information-768-PSCH-ReconfRqst							ProtocolIE-ID ::= 769
id-hS-SCCH-InformationModify-768-PSCH-ReconfRqst					ProtocolIE-ID ::= 770
id-hsSCCH-Specific-Information-ResponseTDD768						ProtocolIE-ID ::= 771
id-E-DPCH-Information-RL-AdditionReqFDD								ProtocolIE-ID ::= 772
id-PDSCH-Timeslot-Format-PSCH-ReconfRqst-LCR						ProtocolIE-ID ::= 775
id-PUSCH-Timeslot-Format-PSCH-ReconfRqst-LCR						ProtocolIE-ID ::= 780
id-E-DCH-PowerOffset-for-SchedulingInfo								ProtocolIE-ID ::= 782
id-HSDSCH-Configured-Indicator										ProtocolIE-ID ::= 783
id-Rx-Timing-Deviation-Value-384-ext								ProtocolIE-ID ::= 786
id-RTWP-ReportingIndicator											ProtocolIE-ID ::= 787
id-RTWP-CellPortion-ReportingIndicator								ProtocolIE-ID ::= 788
id-Received-Scheduled-EDCH-Power-Share-Value						ProtocolIE-ID ::= 789
id-Received-Scheduled-EDCH-Power-Share-For-CellPortion-Value		ProtocolIE-ID ::= 790
id-Received-Scheduled-EDCH-Power-Share								ProtocolIE-ID ::= 791
id-Received-Scheduled-EDCH-Power-Share-For-CellPortion				ProtocolIE-ID ::= 792
id-tFCI-Presence													ProtocolIE-ID ::= 793
id-HSSICH-TPC-StepSize										ProtocolIE-ID ::= 794
id-E-RUCCH-InformationList-AuditRsp									ProtocolIE-ID ::= 795
id-E-RUCCH-InformationList-ResourceStatusInd						ProtocolIE-ID ::= 796
id-E-DCH-TDD-CapacityConsumptionLaw									ProtocolIE-ID ::= 797
id-E-RUCCH-Information												ProtocolIE-ID ::= 798
id-E-DCH-Information												ProtocolIE-ID ::= 799
id-E-DCH-Information-Response										ProtocolIE-ID ::= 800
id-E-DCH-Information-Reconfig										ProtocolIE-ID ::= 801
id-E-PUCH-Information-PSCH-ReconfRqst								ProtocolIE-ID ::= 802
id-Add-To-E-AGCH-Resource-Pool-PSCH-ReconfRqst						ProtocolIE-ID ::= 803
id-Modify-E-AGCH-Resource-Pool-PSCH-ReconfRqst						ProtocolIE-ID ::= 804
id-Delete-From-E-AGCH-Resource-Pool-PSCH-ReconfRqst					ProtocolIE-ID ::= 805
id-E-HICH-Information-PSCH-ReconfRqst								ProtocolIE-ID ::= 806
id-E-HICH-TimeOffset												ProtocolIE-ID ::= 807
id-Maximum-Generated-ReceivedTotalWideBandPowerInOtherCells			ProtocolIE-ID ::= 808
id-E-DCH-Serving-RL-ID 												ProtocolIE-ID ::= 809
id-E-RUCCH-768-InformationList-AuditRsp								ProtocolIE-ID ::= 810
id-E-RUCCH-768-InformationList-ResourceStatusInd					ProtocolIE-ID ::= 811
id-E-RUCCH-768-Information											ProtocolIE-ID ::= 812
id-E-DCH-768-Information											ProtocolIE-ID ::= 813
id-E-DCH-768-Information-Reconfig									ProtocolIE-ID ::= 814
id-E-PUCH-Information-768-PSCH-ReconfRqst							ProtocolIE-ID ::= 815
id-Add-To-E-AGCH-Resource-Pool-768-PSCH-ReconfRqst					ProtocolIE-ID ::= 816
id-Modify-E-AGCH-Resource-Pool-768-PSCH-ReconfRqst					ProtocolIE-ID ::= 817
id-E-HICH-Information-768-PSCH-ReconfRqst							ProtocolIE-ID ::= 818
id-ExtendedPropagationDelay											ProtocolIE-ID ::= 819
id-Extended-Round-Trip-Time-Value									ProtocolIE-ID ::= 820
id-AlternativeFormatReportingIndicator								ProtocolIE-ID ::= 821
id-DCH-Indicator-For-E-DCH-HSDPA-Operation							ProtocolIE-ID ::= 822
id-Reference-ReceivedTotalWideBandPowerReporting					ProtocolIE-ID ::= 823
id-Reference-ReceivedTotalWideBandPowerSupportIndicator				ProtocolIE-ID ::= 824
id-ueCapability-Info												ProtocolIE-ID ::= 825
id-MAChs-ResetIndicator												ProtocolIE-ID ::= 826
id-Fast-Reconfiguration-Mode										ProtocolIE-ID ::= 827
id-Fast-Reconfiguration-Permission									ProtocolIE-ID ::= 828
id-BroadcastReference												ProtocolIE-ID ::= 829
id-BroadcastCommonTransportBearerIndication							ProtocolIE-ID ::= 830
id-ContinuousPacketConnectivityDTX-DRX-Capability					ProtocolIE-ID ::= 831
id-ContinuousPacketConnectivityDTX-DRX-Information					ProtocolIE-ID ::= 832
id-ContinuousPacketConnectivityHS-SCCH-less-Capability				ProtocolIE-ID ::= 833
id-ContinuousPacketConnectivityHS-SCCH-less-Information				ProtocolIE-ID ::= 834
id-ContinuousPacketConnectivityHS-SCCH-less-Information-Response	ProtocolIE-ID ::= 835
id-CPC-Information													ProtocolIE-ID ::= 836
id-MIMO-Capability													ProtocolIE-ID ::= 837
id-MIMO-PilotConfiguration											ProtocolIE-ID ::= 838
id-MBSFN-Cell-ParameterID-Cell-SetupRqstTDD							ProtocolIE-ID ::= 841
id-MBSFN-Cell-ParameterID-Cell-ReconfRqstTDD						ProtocolIE-ID ::= 842
id-S-CCPCH-Modulation												ProtocolIE-ID ::= 843
id-HS-PDSCH-Code-Change-Grant										ProtocolIE-ID ::= 844
id-HS-PDSCH-Code-Change-Indicator									ProtocolIE-ID ::= 845
id-SYNC-UL-Partition-LCR											ProtocolIE-ID ::= 846
id-E-DCH-LCR-Information											ProtocolIE-ID ::= 847
id-E-DCH-LCR-Information-Reconfig									ProtocolIE-ID ::= 848
id-E-PUCH-Information-LCR-PSCH-ReconfRqst							ProtocolIE-ID ::= 852
id-Add-To-E-AGCH-Resource-Pool-LCR-PSCH-ReconfRqst					ProtocolIE-ID ::= 853
id-Modify-E-AGCH-Resource-Pool-LCR-PSCH-ReconfRqst					ProtocolIE-ID ::= 854
id-Add-To-E-HICH-Resource-Pool-LCR-PSCH-ReconfRqst					ProtocolIE-ID ::= 855
id-Modify-E-HICH-Resource-Pool-LCR-PSCH-ReconfRqst					ProtocolIE-ID ::= 856
id-Delete-From-E-HICH-Resource-Pool-PSCH-ReconfRqst					ProtocolIE-ID ::= 857
id-E-HICH-TimeOffsetLCR												ProtocolIE-ID ::= 858
id-SixtyfourQAM-DL-Capability										ProtocolIE-ID ::= 860
id-SixteenQAM-UL-Capability											ProtocolIE-ID ::= 861
id-HSDSCH-MACdPDU-SizeCapability									ProtocolIE-ID ::= 864
id-HSDSCH-MACdPDUSizeFormat 										ProtocolIE-ID ::= 865
id-MaximumMACdPDU-SizeExtended										ProtocolIE-ID ::= 866
id-F-DPCH-SlotFormat												ProtocolIE-ID ::= 870
id-F-DPCH-SlotFormatCapability										ProtocolIE-ID ::= 871
id-LCRTDD-uplink-Physical-Channel-Capability						ProtocolIE-ID ::= 872
id-Extended-RNC-ID													ProtocolIE-ID ::= 873
id-Max-UE-DTX-Cycle													ProtocolIE-ID ::= 874
id-Secondary-CCPCH-SlotFormat-Extended								ProtocolIE-ID ::= 876
id-MBSFN-Only-Mode-Indicator-Cell-SetupRqstTDD-LCR					ProtocolIE-ID ::= 878
id-MBSFN-Only-Mode-Capability										ProtocolIE-ID ::= 879
id-Time-Slot-Parameter-ID											ProtocolIE-ID ::= 880
id-Additional-failed-HS-SICH										ProtocolIE-ID ::= 881
id-Additional-missed-HS-SICH										ProtocolIE-ID ::= 882
id-Additional-total-HS-SICH											ProtocolIE-ID ::= 883
id-Additional-HS-SICH-Reception-Quality-Measurement-Value			ProtocolIE-ID ::= 884
id-GANSS-Common-Data												ProtocolIE-ID ::= 887
id-GANSS-Information												ProtocolIE-ID ::= 888
id-GANSS-Generic-Data												ProtocolIE-ID ::= 889
id-TUTRANGANSSMeasurementThresholdInformation						ProtocolIE-ID ::= 890
id-TUTRANGANSSMeasurementValueInformation							ProtocolIE-ID ::= 891
id-ModulationPO-MBSFN												ProtocolIE-ID ::= 892
id-Enhanced-FACH-Capability											ProtocolIE-ID ::= 895
id-Enhanced-PCH-Capability											ProtocolIE-ID ::= 896
id-HSDSCH-Common-System-InformationFDD								ProtocolIE-ID ::= 897
id-HSDSCH-Common-System-Information-ResponseFDD						ProtocolIE-ID ::= 898
id-HSDSCH-Paging-System-InformationFDD								ProtocolIE-ID ::= 899
id-HSDSCH-Paging-System-Information-ResponseFDD						ProtocolIE-ID ::= 900
id-MBMS-Capability													ProtocolIE-ID ::= 901
id-Ext-Reference-E-TFCI-PO											ProtocolIE-ID ::= 902
id-Ext-Max-Bits-MACe-PDU-non-scheduled								ProtocolIE-ID ::= 903
id-HARQ-MemoryPartitioningInfoExtForMIMO							ProtocolIE-ID ::= 904
id-MIMO-ActivationIndicator											ProtocolIE-ID ::= 905
id-MIMO-Mode-Indicator												ProtocolIE-ID ::= 906
id-MIMO-N-M-Ratio													ProtocolIE-ID ::= 907
id-IPMulticastIndication											ProtocolIE-ID ::= 908
id-IPMulticastDataBearerIndication									ProtocolIE-ID ::= 909
id-TransportBearerNotSetupIndicator									ProtocolIE-ID ::= 910
id-TransportBearerNotRequestedIndicator								ProtocolIE-ID ::= 911
id-TimeSlotConfigurationList-LCR-CTCH-SetupRqstTDD					ProtocolIE-ID ::= 912
id-Cell-Frequency-List-Information-LCR-MulFreq-AuditRsp				ProtocolIE-ID ::= 913
id-Cell-Frequency-List-InformationItem-LCR-MulFreq-AuditRsp			ProtocolIE-ID ::= 914
id-Cell-Frequency-List-LCR-MulFreq-Cell-SetupRqstTDD				ProtocolIE-ID ::= 915
id-UARFCN-Adjustment												ProtocolIE-ID ::= 916
id-Cell-Frequency-List-Information-LCR-MulFreq-ResourceStatusInd	ProtocolIE-ID ::= 917
id-Cell-Frequency-List-InformationItem-LCR-MulFreq-ResourceStatusInd	ProtocolIE-ID ::= 918
id-UPPCHPositionLCR													ProtocolIE-ID ::= 919
id-UPPCH-LCR-Parameters-CTCH-ReconfRqstTDD							ProtocolIE-ID ::= 920
id-UPPCH-LCR-InformationList-AuditRsp								ProtocolIE-ID ::= 921
id-UPPCH-LCR-InformationItem-AuditRsp								ProtocolIE-ID ::= 922
id-UPPCH-LCR-InformationList-ResourceStatusInd						ProtocolIE-ID ::= 923
id-UPPCH-LCR-InformationItem-ResourceStatusInd						ProtocolIE-ID ::= 924
id-multipleFreq-dL-HS-PDSCH-Timeslot-Information-LCR-PSCH-ReconfRqst	ProtocolIE-ID ::= 925
id-number-Of-Supported-Carriers										ProtocolIE-ID ::= 926
id-multipleFreq-HSPDSCH-InformationList-ResponseTDDLCR				ProtocolIE-ID ::= 927
id-Unsuccessful-UARFCNItem-PSCH-ReconfFailureTDD					ProtocolIE-ID ::= 928
id-multipleFreq-HS-DSCH-Resources-InformationList-AuditRsp			ProtocolIE-ID ::= 929
id-multipleFreq-HS-DSCH-Resources-InformationList-ResourceStatusInd	ProtocolIE-ID ::= 930
id-UARFCNSpecificCauseList											ProtocolIE-ID ::= 931
id-tSN-Length														ProtocolIE-ID ::= 932
id-MultipleFreq-DL-HS-PDSCH-Timeslot-Information-LCRItem-PSCH-ReconfRqst	ProtocolIE-ID ::= 933
id-multicarrier-number												ProtocolIE-ID ::= 934
id-Extended-HS-SCCH-ID												ProtocolIE-ID ::= 935
id-Extended-HS-SICH-ID												ProtocolIE-ID ::= 936
id-HSSICH-InfoExt-DM-Rqst											ProtocolIE-ID ::= 937
id-Delete-From-HS-SCCH-Resource-PoolExt-PSCH-ReconfRqst				ProtocolIE-ID ::= 938
id-HS-SCCH-InformationExt-LCR-PSCH-ReconfRqst						ProtocolIE-ID ::= 939
id-HS-SCCH-InformationModifyExt-LCR-PSCH-ReconfRqst					ProtocolIE-ID ::= 940
id-PowerControlGAP													ProtocolIE-ID ::= 941
id-MBSFN-SpecialTimeSlot-LCR										ProtocolIE-ID ::= 942
id-Common-MACFlows-to-DeleteFDD										ProtocolIE-ID ::= 943
id-Paging-MACFlows-to-DeleteFDD										ProtocolIE-ID ::= 944
id-E-TFCI-Boost-Information											ProtocolIE-ID ::= 945
id-SixteenQAM-UL-Operation-Indicator								ProtocolIE-ID ::= 946
id-SixtyfourQAM-UsageAllowedIndicator								ProtocolIE-ID ::= 947
id-SixtyfourQAM-DL-UsageIndicator									ProtocolIE-ID ::= 948
id-Default-Serving-Grant-in-DTX-Cycle2								ProtocolIE-ID ::= 949
id-Maximum-Target-ReceivedTotalWideBandPower-LCR					ProtocolIE-ID ::= 950
id-E-DPDCH-PowerInterpolation										ProtocolIE-ID ::= 951

END
