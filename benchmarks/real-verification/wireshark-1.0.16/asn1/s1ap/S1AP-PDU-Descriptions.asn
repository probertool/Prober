-- $Id: S1AP-PDU-Descriptions.asn 23884 2007-12-16 13:34:33Z etxrab $
-- 9.3.2	Elementary Procedure Definitions
-- **************************************************************
--
-- Elementary Procedure definitions
--
-- **************************************************************

S1AP-PDU-Descriptions  { 
itu-t (0) identified-organization (4) etsi (0) mobileDomain (0) 
eps-Access (20) modules (3) s1ap (1) version1 (1) s1ap-PDU-Descriptions (0)}

DEFINITIONS AUTOMATIC TAGS ::= 

BEGIN

-- **************************************************************
--
-- IE parameter types from other modules.
--
-- **************************************************************

IMPORTS
	Criticality,
	ProcedureCode
FROM S1AP-CommonDataTypes

	HandoverRequired,
	HandoverCommand,
	HandoverPreparationFailure,
	HandoverRequest,
	HandoverRequestAcknowledge,
	HandoverFailure,
	HandoverNotify,
	PathSwitchRequest,
	PathSwitchRequestAcknowledge,
	PathSwitchRequestFailure,	
	SAEBearerSetupRequest,
	SAEBearerSetupResponse,
	SAEBearerModifyRequest,
	SAEBearerModifyResponse,
	SAEBearerReleaseCommand,
	SAEBearerReleaseComplete,
	SAEBearerReleaseRequest,
	InitialContextSetupRequest,
	InitialContextSetupResponse,
	InitialContextSetupFailure,
	Paging,
	DownlinkNASTransport,
	InitialUEMessage,
	UplinkNASTransport,
	HandoverCancel,
	HandoverCancelAcknowledge,
	Reset,
	ResetAcknowledge,
	ErrorIndication,
	NASNonDeliveryIndication,
	S1SetupRequest,
	S1SetupResponse,
	S1SetupFailure,
	UEContextReleaseRequest

FROM S1AP-PDU-Contents
	
	id-HandoverPreparation,
	id-HandoverResourceAllocation,
	id-HandoverNotification,
	id-PathSwitchRequest,
	id-SAEBearerSetup,
	id-SAEBearerModify,
	id-SAEBearerRelease,
	id-SAEBearerReleaseRequest,
	id-InitialContextSetup,
	id-Paging,
	id-downlinkNASTransport,
	id-initialUEMessage,
	id-uplinkNASTransport,
	id-HandoverCancel,
	id-Reset,
	id-ErrorIndication,
	id-NASNonDeliveryIndication,
	id-S1Setup,
	id-UEContextReleaseRequest
FROM S1AP-Constants;


-- **************************************************************
--
-- Interface Elementary Procedure Class
--
-- **************************************************************

S1AP-ELEMENTARY-PROCEDURE ::= CLASS {
	&InitiatingMessage				,
	&SuccessfulOutcome				OPTIONAL,
	&UnsuccessfulOutcome				OPTIONAL,
	&procedureCode			ProcedureCode 	UNIQUE,
	&criticality			Criticality 	DEFAULT ignore
}
WITH SYNTAX {
	INITIATING MESSAGE		&InitiatingMessage
	[SUCCESSFUL OUTCOME		&SuccessfulOutcome]
	[UNSUCCESSFUL OUTCOME		&UnsuccessfulOutcome]
	PROCEDURE CODE				&procedureCode
	[CRITICALITY			&criticality]
}

-- **************************************************************
--
-- Interface PDU Definition
--
-- **************************************************************

S1AP-PDU ::= CHOICE {
	initiatingMessage	InitiatingMessage,
	successfulOutcome	SuccessfulOutcome,
	unsuccessfulOutcome	UnsuccessfulOutcome,
	...
}

InitiatingMessage ::= SEQUENCE {
	procedureCode	S1AP-ELEMENTARY-PROCEDURE.&procedureCode	({S1AP-ELEMENTARY-PROCEDURES}),
	criticality	S1AP-ELEMENTARY-PROCEDURE.&criticality		({S1AP-ELEMENTARY-PROCEDURES}{@procedureCode}),
	value		S1AP-ELEMENTARY-PROCEDURE.&InitiatingMessage	({S1AP-ELEMENTARY-PROCEDURES}{@procedureCode})
}

SuccessfulOutcome ::= SEQUENCE {
	procedureCode	S1AP-ELEMENTARY-PROCEDURE.&procedureCode	({S1AP-ELEMENTARY-PROCEDURES}),
	criticality	S1AP-ELEMENTARY-PROCEDURE.&criticality		({S1AP-ELEMENTARY-PROCEDURES}{@procedureCode}),
	value		S1AP-ELEMENTARY-PROCEDURE.&SuccessfulOutcome	({S1AP-ELEMENTARY-PROCEDURES}{@procedureCode})
}

UnsuccessfulOutcome ::= SEQUENCE {
	procedureCode	S1AP-ELEMENTARY-PROCEDURE.&procedureCode	({S1AP-ELEMENTARY-PROCEDURES}),
	criticality	S1AP-ELEMENTARY-PROCEDURE.&criticality		({S1AP-ELEMENTARY-PROCEDURES}{@procedureCode}),
	value		S1AP-ELEMENTARY-PROCEDURE.&UnsuccessfulOutcome	({S1AP-ELEMENTARY-PROCEDURES}{@procedureCode})
}

-- **************************************************************
--
-- Interface Elementary Procedure List
--
-- **************************************************************

S1AP-ELEMENTARY-PROCEDURES S1AP-ELEMENTARY-PROCEDURE ::= {
	S1AP-ELEMENTARY-PROCEDURES-CLASS-1		|
	S1AP-ELEMENTARY-PROCEDURES-CLASS-2,	
	...
}


S1AP-ELEMENTARY-PROCEDURES-CLASS-1 S1AP-ELEMENTARY-PROCEDURE ::= {
	handoverPreparation				|
	handoverResourceAllocation		|
	pathSwitchRequest 				|
	sAEbearerSetup					|
	sAEbearerModify					|
	sAEbearerRelease				|
	initialContextSetup				|
	handoverCancel					|
	reset							|
	s1Setup,
	...
}

S1AP-ELEMENTARY-PROCEDURES-CLASS-2 S1AP-ELEMENTARY-PROCEDURE ::= {	
	handoverNotification			|
	sAEbearerReleaseRequest			|
	paging 							|
	downlinkNASTransport						|
	initialUEMessage							|
	uplinkNASTransport				|
	errorIndication					|
	nASNonDeliveryIndication		|
	uEContextReleaseRequest			,
	...
}

-- **************************************************************
--
-- Interface Elementary Procedures
--
-- **************************************************************

handoverPreparation S1AP-ELEMENTARY-PROCEDURE ::= {
	INITIATING MESSAGE	HandoverRequired
	SUCCESSFUL OUTCOME	HandoverCommand
	UNSUCCESSFUL OUTCOME	HandoverPreparationFailure
	PROCEDURE CODE			id-HandoverPreparation
	CRITICALITY		reject
}

handoverResourceAllocation S1AP-ELEMENTARY-PROCEDURE ::= {
	INITIATING MESSAGE	HandoverRequest
	SUCCESSFUL OUTCOME	HandoverRequestAcknowledge
	UNSUCCESSFUL OUTCOME	HandoverFailure
	PROCEDURE CODE			id-HandoverResourceAllocation
	CRITICALITY		reject
}

handoverNotification S1AP-ELEMENTARY-PROCEDURE ::= {
	INITIATING MESSAGE	HandoverNotify
	PROCEDURE CODE			id-HandoverNotification
	CRITICALITY		reject
}

pathSwitchRequest S1AP-ELEMENTARY-PROCEDURE ::= {
	INITIATING MESSAGE	PathSwitchRequest
	SUCCESSFUL OUTCOME	PathSwitchRequestAcknowledge
	UNSUCCESSFUL OUTCOME	PathSwitchRequestFailure
	PROCEDURE CODE			id-PathSwitchRequest
	CRITICALITY		reject
}

sAEbearerSetup S1AP-ELEMENTARY-PROCEDURE ::= {
	INITIATING MESSAGE	SAEBearerSetupRequest
	SUCCESSFUL OUTCOME	SAEBearerSetupResponse
	PROCEDURE CODE		id-SAEBearerSetup
	CRITICALITY		reject
}

sAEbearerModify S1AP-ELEMENTARY-PROCEDURE ::= {
	INITIATING MESSAGE	SAEBearerModifyRequest
	SUCCESSFUL OUTCOME	SAEBearerModifyResponse
	PROCEDURE CODE		id-SAEBearerModify
	CRITICALITY		reject
}

sAEbearerRelease S1AP-ELEMENTARY-PROCEDURE ::= {
	INITIATING MESSAGE	SAEBearerReleaseCommand
	SUCCESSFUL OUTCOME	SAEBearerReleaseComplete
	PROCEDURE CODE		id-SAEBearerRelease
	CRITICALITY		reject
}

sAEbearerReleaseRequest S1AP-ELEMENTARY-PROCEDURE ::= {
	INITIATING MESSAGE	SAEBearerReleaseRequest
	PROCEDURE CODE		id-SAEBearerReleaseRequest
	CRITICALITY		ignore
}

initialContextSetup S1AP-ELEMENTARY-PROCEDURE ::= {
	INITIATING MESSAGE	InitialContextSetupRequest
	SUCCESSFUL OUTCOME	InitialContextSetupResponse
	UNSUCCESSFUL OUTCOME InitialContextSetupFailure
	PROCEDURE CODE		id-InitialContextSetup
	CRITICALITY		reject
}

uEContextReleaseRequest S1AP-ELEMENTARY-PROCEDURE ::= {
	INITIATING MESSAGE		UEContextReleaseRequest
	PROCEDURE CODE			id-UEContextReleaseRequest
	CRITICALITY				ignore
}

paging S1AP-ELEMENTARY-PROCEDURE ::= {
	INITIATING MESSAGE	Paging
	PROCEDURE CODE		id-Paging
	CRITICALITY			ignore
}

downlinkNASTransport S1AP-ELEMENTARY-PROCEDURE ::= {
	INITIATING MESSAGE		DownlinkNASTransport
	PROCEDURE CODE			id-downlinkNASTransport
	CRITICALITY				ignore
}

initialUEMessage S1AP-ELEMENTARY-PROCEDURE ::= {
	INITIATING MESSAGE		InitialUEMessage
	PROCEDURE CODE			id-initialUEMessage
	CRITICALITY				ignore
}

uplinkNASTransport S1AP-ELEMENTARY-PROCEDURE ::= {
	INITIATING MESSAGE		UplinkNASTransport
	PROCEDURE CODE			id-uplinkNASTransport
	CRITICALITY				ignore
}
nASNonDeliveryIndication S1AP-ELEMENTARY-PROCEDURE ::= {
	INITIATING MESSAGE		NASNonDeliveryIndication
	PROCEDURE CODE			id-NASNonDeliveryIndication
	CRITICALITY				ignore
}

handoverCancel S1AP-ELEMENTARY-PROCEDURE ::= {
	INITIATING MESSAGE	HandoverCancel
	SUCCESSFUL OUTCOME	HandoverCancelAcknowledge
	PROCEDURE CODE			id-HandoverCancel
	CRITICALITY		reject
}

reset S1AP-ELEMENTARY-PROCEDURE ::= {
	INITIATING MESSAGE	Reset
	SUCCESSFUL OUTCOME	ResetAcknowledge
	PROCEDURE CODE		id-Reset
	CRITICALITY			reject
}

errorIndication S1AP-ELEMENTARY-PROCEDURE ::= {
	INITIATING MESSAGE	ErrorIndication
	PROCEDURE CODE		id-ErrorIndication
	CRITICALITY		ignore
}

s1Setup S1AP-ELEMENTARY-PROCEDURE ::= {
	INITIATING MESSAGE		S1SetupRequest
	SUCCESSFUL OUTCOME		S1SetupResponse
	UNSUCCESSFUL OUTCOME 	S1SetupFailure
	PROCEDURE CODE			id-S1Setup
	CRITICALITY				reject
}

END
